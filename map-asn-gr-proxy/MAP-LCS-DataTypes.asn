-- ETSI TS 129 002 V10.4.0 (2011-10)
-- 17.7.13 Location service data types

MAP-LCS-DataTypes {
   itu-t identified-organization (4) etsi (0) mobileDomain (0)
   gsm-Network (1) modules (3) map-LCS-DataTypes (25) version13 (13)}

DEFINITIONS
IMPLICIT TAGS
::=
BEGIN

--unused:EXPORTS
--unused:	RoutingInfoForLCS-Arg,
--unused:	RoutingInfoForLCS-Res,
--unused:	ProvideSubscriberLocation-Arg,
--unused:	ProvideSubscriberLocation-Res,
--unused:	SubscriberLocationReport-Arg,
--unused:	SubscriberLocationReport-Res,
--unused:	LocationType, 
--unused:	DeferredLocationEventType,
--unused:	LCSClientName,
--unused:	LCS-QoS,
--unused:	Horizontal-Accuracy,
--unused:	ResponseTime,
--unused:	Ext-GeographicalInformation, 
--unused:	VelocityEstimate,
--unused:	SupportedGADShapes,
--unused:	Add-GeographicalInformation,
--unused:	LCSRequestorID, 
--unused:	LCS-ReferenceNumber,
--unused:	LCSCodeword,
--unused:	AreaEventInfo,
--unused:	ReportingPLMNList,
--unused:	PeriodicLDRInfo,
--unused:	SequenceNumber
--unused:;

IMPORTS
	AddressString,
	ISDN-AddressString,
	IMEI,
	IMSI,
	LMSI,
	SubscriberIdentity,
	AgeOfLocationInformation,
	LCSClientExternalID,
	LCSClientInternalID,
	--unused:LCSServiceTypeID,
	CellGlobalIdOrServiceAreaIdOrLAI--unused:,
	--unused:PLMN-Id,
	--unused:GSN-Address,
	--unused:DiameterIdentity
FROM MAP-CommonDataTypes {
   itu-t identified-organization (4) etsi (0) mobileDomain (0)
   gsm-Network (1) modules (3) map-CommonDataTypes (18) version13 (13)}

	ExtensionContainer,
	SLR-ArgExtensionContainer
FROM MAP-ExtensionDataTypes {
   itu-t identified-organization (4) etsi (0) mobileDomain (0)
   gsm-Network (1) modules (3) map-ExtensionDataTypes (21) version13 (13)}

	USSD-DataCodingScheme,
	USSD-String
FROM MAP-SS-DataTypes {
   itu-t identified-organization (4) etsi (0) mobileDomain (0) gsm-Network (1) modules (3)
   map-SS-DataTypes (14) version13 (13)}

	APN--unused:,
	--unused:SupportedLCS-CapabilitySets
FROM MAP-MS-DataTypes {
   itu-t identified-organization (4) etsi (0) mobileDomain (0)
   gsm-Network (1) modules (3) map-MS-DataTypes (11) version13 (13)}

--unused:	Additional-Number
--unused:FROM MAP-SM-DataTypes {
--unused:   itu-t identified-organization (4) etsi (0) mobileDomain (0)
--unused:   gsm-Network (1) modules (3) map-SM-DataTypes (16) version13 (13)}
;


RoutingInfoForLCS-Arg ::= SEQUENCE {
	mlcNumber		[0] ISDN-AddressString, --unused
	targetMS		[1] SubscriberIdentity,
	--unused:extensionContainer	[2] ExtensionContainer	OPTIONAL,
	...}

RoutingInfoForLCS-Res ::= SEQUENCE {
	targetMS		[0] SubscriberIdentity,
	lcsLocationInfo	[1] LCSLocationInfo,    --unused
	--unused:extensionContainer	[2] ExtensionContainer	OPTIONAL,
	...--unused:,
	--unused:v-gmlc-Address	[3]	GSN-Address	OPTIONAL,
	--unused:h-gmlc-Address	[4]	GSN-Address	OPTIONAL,
	--unused:ppr-Address	[5]	GSN-Address	OPTIONAL,
	--unused:additional-v-gmlc-Address	[6]	GSN-Address	OPTIONAL-- }

LCSLocationInfo ::= SEQUENCE {
	networkNode-Number	ISDN-AddressString,
	-- NetworkNode-number can be msc-number, sgsn-number or a dummy value of "0"
	lmsi			[0] LMSI		OPTIONAL,
	extensionContainer	[1] ExtensionContainer	OPTIONAL,
	...,
	gprsNodeIndicator 	[2] NULL		OPTIONAL --unused:,
	-- gprsNodeIndicator is set only if the SGSN number is sent as the Network Node Number
	--unused:additional-Number	[3] Additional-Number	OPTIONAL,
	--unused:supportedLCS-CapabilitySets	[4]	SupportedLCS-CapabilitySets	OPTIONAL,
	--unused:additional-LCS-CapabilitySets	[5]	SupportedLCS-CapabilitySets	OPTIONAL,
	--unused:mme-Name		[6]	DiameterIdentity	OPTIONAL,
	--unused:aaa-Server-Name	[8]	DiameterIdentity	OPTIONAL
	}

ProvideSubscriberLocation-Arg ::= SEQUENCE {
	locationType	LocationType,
	mlc-Number	ISDN-AddressString,
	lcs-ClientID	[0] LCS-ClientID	OPTIONAL,
	privacyOverride	[1] NULL		OPTIONAL,
	imsi			[2] IMSI		OPTIONAL,
	msisdn		[3] ISDN-AddressString	OPTIONAL,
	lmsi			[4] LMSI		OPTIONAL,
	imei			[5] IMEI		OPTIONAL,
	--unsued:lcs-Priority	[6] LCS-Priority	OPTIONAL,
	--unsued:lcs-QoS		[7] LCS-QoS	OPTIONAL,
	--unsued:extensionContainer	[8] ExtensionContainer	OPTIONAL,
	... --unused:,
	--unused:supportedGADShapes	[9]	SupportedGADShapes	OPTIONAL,
	--unused:lcs-ReferenceNumber	[10]	LCS-ReferenceNumber	OPTIONAL,
	--unused:lcsServiceTypeID	[11]	LCSServiceTypeID	OPTIONAL,
	--unused:lcsCodeword	[12]	LCSCodeword	OPTIONAL,
	--unused:lcs-PrivacyCheck	[13]	LCS-PrivacyCheck	OPTIONAL,
	--unused:areaEventInfo	[14]	AreaEventInfo	OPTIONAL,
	--unused:h-gmlc-Address	[15]	GSN-Address	OPTIONAL,
	--unused:mo-lrShortCircuitIndicator	[16] NULL		OPTIONAL,
	--unused:periodicLDRInfo	[17] PeriodicLDRInfo	OPTIONAL,
	--unused:reportingPLMNList	[18] ReportingPLMNList	OPTIONAL-- }

	-- one of imsi or msisdn is mandatory
	-- If a location estimate type indicates activate deferred location or cancel deferred 
	-- location, a lcs-Reference number shall be included.

LocationType ::= SEQUENCE {
	locationEstimateType	[0] LocationEstimateType,
	...,
	deferredLocationEventType	[1] DeferredLocationEventType	OPTIONAL }

LocationEstimateType ::= ENUMERATED {
	currentLocation	(0),
	currentOrLastKnownLocation	(1),
	initialLocation	(2),
	...,
	activateDeferredLocation	(3),
	cancelDeferredLocation	(4) ,
	notificationVerificationOnly	(5) }
--	exception handling:
--	a ProvideSubscriberLocation-Arg containing an unrecognized LocationEstimateType
--	shall be rejected by the receiver with a return error cause of unexpected data value

DeferredLocationEventType ::= BIT STRING {
	msAvailable	(0) ,
	enteringIntoArea	(1),
	leavingFromArea	(2),
	beingInsideArea	(3) ,
	periodicLDR	(4)  } (SIZE (1..16)) 
-- beingInsideArea is always treated as oneTimeEvent regardless of the possible value
-- of occurrenceInfo inside areaEventInfo.
-- exception handling:
-- a ProvideSubscriberLocation-Arg containing other values than listed above in 
-- DeferredLocationEventType shall be rejected by the receiver with a return error cause of 
-- unexpected data value.

LCS-ClientID ::= SEQUENCE {
	lcsClientType	[0] LCSClientType,
	lcsClientExternalID	[1] LCSClientExternalID	OPTIONAL,
	lcsClientDialedByMS	[2] AddressString	OPTIONAL,
	lcsClientInternalID	[3] LCSClientInternalID	OPTIONAL,
	--unused:lcsClientName	[4] LCSClientName	OPTIONAL,
	... --unused:,
	--unused:lcsAPN		[5] APN		OPTIONAL,
	--unused:lcsRequestorID	[6] LCSRequestorID	OPTIONAL-- }

LCSClientType ::= ENUMERATED {
	emergencyServices	(0),
	valueAddedServices	(1),
	plmnOperatorServices	(2),
	lawfulInterceptServices	(3),
	... }
	--	exception handling:
	--	unrecognized values may be ignored if the LCS client uses the privacy override
	--	otherwise, an unrecognized value shall be treated as unexpected data by a receiver
	--	a return error shall then be returned if received in a MAP invoke 

LCSClientName ::= SEQUENCE {
	dataCodingScheme	[0] USSD-DataCodingScheme,
	nameString	[2] NameString,
	...,
	lcs-FormatIndicator	[3] LCS-FormatIndicator	OPTIONAL }

-- The USSD-DataCodingScheme shall indicate use of the default alphabet through the
-- following encoding
--	bit	7 6 5 4 3 2 1 0
--		0 0 0 0 1 1 1 1

NameString ::= USSD-String (SIZE (1..maxNameStringLength))

maxNameStringLength  INTEGER ::= 63

LCSRequestorID ::= SEQUENCE {
	dataCodingScheme	[0] USSD-DataCodingScheme,
	requestorIDString	[1] RequestorIDString,
	...,
	lcs-FormatIndicator	[2] LCS-FormatIndicator	OPTIONAL }

RequestorIDString ::= USSD-String (SIZE (1..maxRequestorIDStringLength))

maxRequestorIDStringLength  INTEGER ::= 63

LCS-FormatIndicator ::= ENUMERATED {
	logicalName	(0),
	e-mailAddress	(1),
	msisdn		(2),
	url			(3),
	sipUrl		(4),
	... }

--unused:LCS-Priority ::= OCTET STRING (SIZE (1))
	-- 0 = highest priority
	-- 1 = normal priority
	-- all other values treated as 1 

--unused:LCS-QoS ::= SEQUENCE {
--unused:	horizontal-accuracy	[0] Horizontal-Accuracy	OPTIONAL,
--unused:	verticalCoordinateRequest	[1] NULL		OPTIONAL,
--unused:	vertical-accuracy	[2] Vertical-Accuracy	OPTIONAL,	
--unused:	responseTime		[3] ResponseTime	OPTIONAL,
--unused:	extensionContainer	[4] ExtensionContainer	OPTIONAL,
--unused:	...,
--unused:	velocityRequest	[5] NULL		OPTIONAL
--unused:}

--unused:Horizontal-Accuracy ::= OCTET STRING (SIZE (1))
	-- bit 8 = 0
	-- bits 7-1 = 7 bit Uncertainty Code defined in 3GPP TS 23.032. The horizontal location 
	-- error should be less than the error indicated by the uncertainty code with 67%
	-- confidence.

--unused:Vertical-Accuracy ::= OCTET STRING (SIZE (1))
	-- bit 8 = 0
	-- bits 7-1 = 7 bit Vertical Uncertainty Code defined in 3GPP TS 23.032. 
	-- The vertical location error should be less than the error indicated 
	-- by the uncertainty code with 67% confidence.

--unused:ResponseTime ::= SEQUENCE {
--unused:	responseTimeCategory	ResponseTimeCategory,
--unused:	...}
--	note: an expandable SEQUENCE simplifies later addition of a numeric response time.

--unused:ResponseTimeCategory ::= ENUMERATED {
--unused:	lowdelay  (0),
--unused:	delaytolerant  (1),
--unused:	... }
--	exception handling:
--	an unrecognized value shall be treated the same as value 1 (delaytolerant)

--unused:SupportedGADShapes ::= BIT STRING {
--unused:	ellipsoidPoint  (0),
--unused:	ellipsoidPointWithUncertaintyCircle (1),
--unused:	ellipsoidPointWithUncertaintyEllipse (2),
--unused:	polygon (3),
--unused:	ellipsoidPointWithAltitude (4),
--unused:	ellipsoidPointWithAltitudeAndUncertaintyElipsoid (5),
--unused:	ellipsoidArc  (6) } (SIZE (7..16))
-- A node shall mark in the BIT STRING all Shapes defined in 3GPP TS 23.032 it supports.
-- exception handling: bits 7 to 15 shall be ignored if received.

--unused:LCS-ReferenceNumber::= OCTET STRING (SIZE(1))

--unused:LCSCodeword ::= SEQUENCE {
--unused:	dataCodingScheme	[0] USSD-DataCodingScheme,
--unused:	lcsCodewordString	[1] LCSCodewordString,
--unused:	...}

--unused:LCSCodewordString ::= USSD-String (SIZE (1..maxLCSCodewordStringLength))

--unused:maxLCSCodewordStringLength  INTEGER ::= 20

--unused:LCS-PrivacyCheck ::= SEQUENCE {
--unused:	callSessionUnrelated	[0] PrivacyCheckRelatedAction,
--unused:	callSessionRelated	[1] PrivacyCheckRelatedAction	OPTIONAL,
--unused:	...}

--unused:PrivacyCheckRelatedAction ::= ENUMERATED {
--unused:	allowedWithoutNotification (0),
--unused:	allowedWithNotification (1),
--unused:	allowedIfNoResponse (2),
--unused:	restrictedIfNoResponse (3),
--unused:	notAllowed (4),
--unused:	...}
--	exception handling:
--	a ProvideSubscriberLocation-Arg containing an unrecognized PrivacyCheckRelatedAction
--	shall be rejected by the receiver with a return error cause of unexpected data value

--unused:AreaEventInfo ::= SEQUENCE {
--unused:	areaDefinition	[0]	AreaDefinition,
--unused:	occurrenceInfo	[1]	OccurrenceInfo	OPTIONAL,
--unused:	intervalTime	[2]	IntervalTime	OPTIONAL,
--unused:	...}

--unused:AreaDefinition ::= SEQUENCE {
--unused:	areaList		[0]	AreaList,
--unused:	...}

--unused:AreaList ::= SEQUENCE SIZE (1..maxNumOfAreas) OF Area

--unused:maxNumOfAreas  INTEGER ::= 10

--unused:Area ::= SEQUENCE {
--unused:	areaType		[0]	AreaType,
--unused:	areaIdentification	[1]	AreaIdentification,
--unused:	...}

--unused:AreaType ::= ENUMERATED {
--unused:	countryCode	(0),
--unused:	plmnId		(1),
--unused:	locationAreaId	(2),
--unused:	routingAreaId	(3),
--unused:	cellGlobalId	(4),
--unused:	...,
--unused:	utranCellId	(5) }

--unused:AreaIdentification ::= OCTET STRING (SIZE (2..7))
	-- The internal structure is defined as follows:
	-- octet 1 bits 4321	Mobile Country Code 1st digit
	--         bits 8765	Mobile Country Code 2nd digit
	-- octet 2 bits 4321	Mobile Country Code 3rd digit
	--         bits 8765	Mobile Network Code 3rd digit if 3 digit MNC included
	--			or filler (1111)
	-- octet 3 bits 4321	Mobile Network Code 1st digit
	--         bits 8765	Mobile Network Code 2nd digit
	-- octets 4 and 5	Location Area Code (LAC) for Local Area Id,
	--			Routing Area Id and Cell Global Id
	-- octet 6	Routing Area Code (RAC) for Routing Area Id
	-- octets 6 and 7	Cell Identity (CI) for Cell Global Id
	-- octets 4 until 7	Utran Cell Identity (UC-Id) for Utran Cell Id

--unused:OccurrenceInfo ::= ENUMERATED {
--unused:	oneTimeEvent	(0),
--unused:	multipleTimeEvent	(1),
--unused:	...}

--unused:IntervalTime ::= INTEGER (1..32767)
	-- minimum interval time between area reports in seconds

--unused:PeriodicLDRInfo ::= SEQUENCE {
--unused:	reportingAmount		ReportingAmount,
--unused:	reportingInterval	ReportingInterval,
--unused:	...}
-- reportingInterval x reportingAmount shall not exceed 8639999 (99 days, 23 hours,
-- 59 minutes and 59 seconds) for compatibility with OMA MLP and RLP

--unused:ReportingAmount ::= INTEGER (1..maxReportingAmount)

--unused:maxReportingAmount INTEGER ::= 8639999

--unused:ReportingInterval ::= INTEGER (1..maxReportingInterval)
-- ReportingInterval is in seconds

--unused:maxReportingInterval INTEGER ::= 8639999

--unused:ReportingPLMNList::= SEQUENCE {
--unused:	plmn-ListPrioritized			[0] NULL					OPTIONAL,
--unused:	plmn-List 						[1] PLMNList,
--unused:	...}

--unused:PLMNList::= SEQUENCE SIZE (1..maxNumOfReportingPLMN) OF
--unused:				ReportingPLMN

--unused:maxNumOfReportingPLMN INTEGER ::= 20

--unused:ReportingPLMN::= SEQUENCE {
--unused:	plmn-Id 						[0] PLMN-Id,
--unused:	ran-Technology 					[1] RAN-Technology			OPTIONAL,
--unused:	ran-PeriodicLocationSupport		[2] NULL					OPTIONAL,
--unused:	...}

--unused:RAN-Technology ::= ENUMERATED {
--unused:	gsm			(0),
--unused:	umts		(1),
--unused:	...}

ProvideSubscriberLocation-Res ::= SEQUENCE {
	locationEstimate	Ext-GeographicalInformation,
	ageOfLocationEstimate	[0] AgeOfLocationInformation	OPTIONAL,
	extensionContainer	[1] ExtensionContainer	OPTIONAL,
	...,
	add-LocationEstimate	[2] Add-GeographicalInformation 	OPTIONAL,
	deferredmt-lrResponseIndicator	[3] NULL		OPTIONAL,
	geranPositioningData	[4] PositioningDataInformation	OPTIONAL,
	utranPositioningData	[5] UtranPositioningDataInfo	OPTIONAL,
	cellIdOrSai	[6] CellGlobalIdOrServiceAreaIdOrLAI	OPTIONAL,
	sai-Present	[7] NULL		OPTIONAL --,
	--unused:accuracyFulfilmentIndicator	[8] AccuracyFulfilmentIndicator	OPTIONAL,
	--unused:velocityEstimate	[9] VelocityEstimate	OPTIONAL,
	--unused:mo-lrShortCircuitIndicator	[10] NULL		OPTIONAL,
	--unused:geranGANSSpositioningData	[11] GeranGANSSpositioningData	OPTIONAL,
	--unused:utranGANSSpositioningData	[12] UtranGANSSpositioningData	OPTIONAL,	
	--unused:targetServingNodeForHandover	[13] ServingNodeAddress	OPTIONAL-- }

--	if deferredmt-lrResponseIndicator is set, locationEstimate is ignored.

-- the add-LocationEstimate parameter shall not be sent to a node that did not indicate the
-- geographic shapes supported in the ProvideSubscriberLocation-Arg
-- The locationEstimate and the add-locationEstimate parameters shall not be sent if
-- the supportedGADShapes parameter has been received in ProvideSubscriberLocation-Arg
-- and the shape encoded in locationEstimate or add-LocationEstimate is not marked
-- as supported in supportedGADShapes. In such a case ProvideSubscriberLocation
-- shall be rejected with error FacilityNotSupported with additional indication
-- shapeOfLocationEstimateNotSupported.
-- sai-Present indicates that the cellIdOrSai parameter contains a Service Area Identity.

--unused:AccuracyFulfilmentIndicator ::= ENUMERATED {
--unused:	requestedAccuracyFulfilled  (0),
--unused:	requestedAccuracyNotFulfilled  (1),
--unused:	...	}

Ext-GeographicalInformation ::= OCTET STRING (SIZE (1..maxExt-GeographicalInformation))
	-- Refers to geographical Information defined in 3GPP TS 23.032.
	-- This is composed of 1 or more octets with an internal structure according to
	-- 3GPP TS 23.032
	-- Octet 1: Type of shape, only the following shapes in 3GPP TS 23.032 are allowed:
	--		(a) Ellipsoid point with uncertainty circle
	--		(b) Ellipsoid point with uncertainty ellipse
	--		(c) Ellipsoid point with altitude and uncertainty ellipsoid
	--		(d) Ellipsoid Arc
	--		(e) Ellipsoid Point
	-- Any other value in octet 1 shall be treated as invalid
	-- Octets 2 to 8 for case (a) – Ellipsoid point with uncertainty circle
	--		Degrees of Latitude				3 octets
	--		Degrees of Longitude				3 octets
	--		Uncertainty code				1 octet
	-- Octets 2 to 11 for case (b) – Ellipsoid point with uncertainty ellipse:
	--		Degrees of Latitude				3 octets
	--		Degrees of Longitude				3 octets
	--		Uncertainty semi-major axis				1 octet
	--		Uncertainty semi-minor axis				1 octet
	--		Angle of major axis				1 octet
	--		Confidence				1 octet
	-- Octets 2 to 14 for case (c) – Ellipsoid point with altitude and uncertainty ellipsoid
	--		Degrees of Latitude				3 octets
	--		Degrees of Longitude				3 octets
	--		Altitude				2 octets
	--		Uncertainty semi-major axis				1 octet
	--		Uncertainty semi-minor axis				1 octet
	--		Angle of major axis				1 octet
	--		Uncertainty altitude				1 octet
	--		Confidence				1 octet
	-- Octets 2 to 13 for case (d) – Ellipsoid Arc
	--		Degrees of Latitude				3 octets
	--		Degrees of Longitude				3 octets
	--		Inner radius				2 octets
	--		Uncertainty radius				1 octet
	--		Offset angle				1 octet
	--		Included angle				1 octet
	--		Confidence				1 octet
	-- Octets 2 to 7 for case (e) – Ellipsoid Point
	--		Degrees of Latitude				3 octets
	--		Degrees of Longitude				3 octets

	--
	-- An Ext-GeographicalInformation parameter comprising more than one octet and
	-- containing any other shape or an incorrect number of octets or coding according
	-- to 3GPP TS 23.032 shall be treated as invalid data by a receiver.
	--
	-- An Ext-GeographicalInformation parameter comprising one octet shall be discarded
	-- by the receiver if an Add-GeographicalInformation parameter is received 
	-- in the same message.
	--
	-- An Ext-GeographicalInformation parameter comprising one octet shall be treated as
	-- invalid data by the receiver if an Add-GeographicalInformation parameter is not
	-- received in the same message.

maxExt-GeographicalInformation  INTEGER ::= 20
	-- the maximum length allows for further shapes in 3GPP TS 23.032 to be included in later 
	-- versions of 3GPP TS 29.002

--unused:VelocityEstimate ::= OCTET STRING (SIZE (4..7))
	-- Refers to Velocity description defined in 3GPP TS 23.032.
	-- This is composed of 4 or more octets with an internal structure according to
	-- 3GPP TS 23.032
	-- Octet 1: Type of velocity, only the following types in 3GPP TS 23.032 are allowed:
	--		(a) Horizontal Velocity
	--		(b) Horizontal with Vertical Velocity
	--		(c) Horizontal Velocity with Uncertainty
	--		(d) Horizontal with Vertical Velocity and Uncertainty
	-- For types Horizontal with Vertical Velocity and Horizontal with Vertical Velocity
	-- and Uncertainty, the direction of the Vertical Speed is also included in Octet 1
	-- Any other value in octet 1 shall be treated as invalid
	-- Octets 2 to 4 for case (a) Horizontal velocity:
	--		Bearing				1 octet
	--		Horizontal Speed				2 octets
	-- Octets 2 to 5 for case (b) – Horizontal with Vertical Velocity:
	--		Bearing				1 octet
	--		Horizontal Speed				2 octets
	--		Vertical Speed				1 octet
	-- Octets 2 to 5 for case (c) – Horizontal velocity with Uncertainty:
	--		Bearing				1 octet
	--		Horizontal Speed				2 octets
	--		Uncertainty Speed				1 octet
	-- Octets 2 to 7 for case (d) – Horizontal with Vertical Velocity and Uncertainty:
	--		Bearing				1 octet
	--		Horizontal Speed				2 octets
	--		Vertical Speed				1 octet
	--		Horizontal Uncertainty Speed			1 octet
	--		Vertical Uncertainty Speed				1 octet

PositioningDataInformation ::= OCTET STRING (SIZE (2..maxPositioningDataInformation))
	-- Refers to the Positioning Data defined in 3GPP TS 49.031.
	-- This is composed of 2 or more octets with an internal structure according to
	-- 3GPP TS 49.031. 

maxPositioningDataInformation INTEGER ::= 10
	-- 

UtranPositioningDataInfo ::= OCTET STRING (SIZE (3..maxUtranPositioningDataInfo))
	-- Refers to the Position Data defined in 3GPP TS 25.413.
	-- This is composed of the positioningDataDiscriminator and the positioningDataSet
	-- included in positionData as defined in 3GPP TS 25.413.

maxUtranPositioningDataInfo INTEGER ::= 11
	-- 

--unused:GeranGANSSpositioningData ::= OCTET STRING (SIZE (2..maxGeranGANSSpositioningData))
	-- Refers to the GANSS Positioning Data defined in 3GPP TS 49.031.
	-- This is composed of 2 or more octets with an internal structure according to
	-- 3GPP TS 49.031. 

--unused:maxGeranGANSSpositioningData INTEGER ::= 10
	-- 

--unused:UtranGANSSpositioningData ::= OCTET STRING (SIZE (1..maxUtranGANSSpositioningData))
	-- Refers to the Position Data defined in 3GPP TS 25.413.
	-- This is composed of the GANSS-PositioningDataSet only, included in PositionData
     -- as defined in 3GPP TS 25.413.

--unused:maxUtranGANSSpositioningData INTEGER ::= 9
	-- 

Add-GeographicalInformation ::= OCTET STRING (SIZE (1..maxAdd-GeographicalInformation))
	-- Refers to geographical Information defined in 3GPP TS 23.032.
	-- This is composed of 1 or more octets with an internal structure according to 
	-- 3GPP TS 23.032
	-- Octet 1: Type of shape, all the shapes defined in 3GPP TS 23.032 are allowed:
	-- Octets 2 to n (where n is the total number of octets necessary to encode the shape
	-- according to 3GPP TS 23.032) are used to encode the shape itself in accordance with the
	-- encoding defined in 3GPP TS 23.032
	--
	-- An Add-GeographicalInformation parameter, whether valid or invalid, received 
	-- together with a valid Ext-GeographicalInformation parameter in the same message 
	-- shall be discarded.
	--
	-- An Add-GeographicalInformation parameter containing any shape not defined in 
	-- 3GPP TS 23.032 or an incorrect number of octets or coding according to 
	-- 3GPP TS 23.032 shall be treated as invalid data by a receiver if not received 
	-- together with a valid Ext-GeographicalInformation parameter in the same message.

maxAdd-GeographicalInformation  INTEGER ::= 91
	-- the maximum length allows support for all the shapes currently defined in 3GPP TS 23.032

SubscriberLocationReport-Arg ::= SEQUENCE {
	lcs-Event		LCS-Event,
	lcs-ClientID	LCS-ClientID, 
	lcsLocationInfo	LCSLocationInfo,
	msisdn		[0] ISDN-AddressString	OPTIONAL,
	imsi			[1] IMSI		OPTIONAL,
	imei			[2] IMEI		OPTIONAL,
	--unused:na-ESRD		[3] ISDN-AddressString	OPTIONAL,
	--unused:na-ESRK		[4] ISDN-AddressString	OPTIONAL,
	--unused:locationEstimate	[5] Ext-GeographicalInformation	OPTIONAL,
	--unused:ageOfLocationEstimate	[6] AgeOfLocationInformation	OPTIONAL,
	--unused:slr-ArgExtensionContainer	[7] SLR-ArgExtensionContainer	OPTIONAL,
	... --unused:,
	--unused:add-LocationEstimate	[8] Add-GeographicalInformation	OPTIONAL,
	--unused:deferredmt-lrData	[9] Deferredmt-lrData	OPTIONAL, 
	--unused:lcs-ReferenceNumber	[10] LCS-ReferenceNumber	OPTIONAL,
	--unused:geranPositioningData	[11] PositioningDataInformation	OPTIONAL,
	--unused:utranPositioningData	[12] UtranPositioningDataInfo	OPTIONAL,
	--unused:cellIdOrSai	[13]	CellGlobalIdOrServiceAreaIdOrLAI	OPTIONAL,
	--unused:h-gmlc-Address	[14]	GSN-Address	OPTIONAL,
	--unused:lcsServiceTypeID	[15]	LCSServiceTypeID	OPTIONAL,
	--unused:sai-Present	[17] NULL		OPTIONAL,
	--unused:pseudonymIndicator	[18] NULL		OPTIONAL,
	--unused:accuracyFulfilmentIndicator	[19] AccuracyFulfilmentIndicator	OPTIONAL,
	--unused:velocityEstimate	[20] VelocityEstimate	OPTIONAL,
	--unused:sequenceNumber	[21] SequenceNumber	OPTIONAL,
	--unused:periodicLDRInfo	[22] PeriodicLDRInfo	OPTIONAL,
	--unused:mo-lrShortCircuitIndicator	[23] NULL		OPTIONAL,
	--unused:geranGANSSpositioningData	[24] GeranGANSSpositioningData	OPTIONAL,
	--unused:utranGANSSpositioningData	[25] UtranGANSSpositioningData	OPTIONAL,
	--unused:targetServingNodeForHandover	[26] ServingNodeAddress	OPTIONAL-- }

	-- one of msisdn or imsi is mandatory
	-- a location estimate that is valid for the locationEstimate parameter should 
	-- be transferred in this parameter in preference to the add-LocationEstimate.
	-- the deferredmt-lrData parameter shall be included if and only if the lcs-Event
	-- indicates a deferredmt-lrResponse.
	-- if the lcs-Event indicates a deferredmt-lrResponse then the locationEstimate 
	-- and the add-locationEstimate parameters shall not be sent if the 
	-- supportedGADShapes parameter had been received in ProvideSubscriberLocation-Arg
	-- and the shape encoded in locationEstimate or add-LocationEstimate was not marked
	-- as supported in supportedGADShapes. In such a case terminationCause 
	-- in deferredmt-lrData shall be present with value 
	-- shapeOfLocationEstimateNotSupported. 
	-- If a lcs event indicates deferred mt-lr response, the lcs-Reference number shall be 
	-- included. 
	-- sai-Present indicates that the cellIdOrSai parameter contains a Service Area Identity.

--unused:Deferredmt-lrData ::= SEQUENCE {
--unused:	deferredLocationEventType	DeferredLocationEventType,
--unused:	terminationCause	[0] TerminationCause	OPTIONAL,
--unused:	lcsLocationInfo	[1] LCSLocationInfo	OPTIONAL,
--unused:	...}
	-- lcsLocationInfo may be included only if a terminationCause is present 
	-- indicating mt-lrRestart.

LCS-Event ::= ENUMERATED {
	emergencyCallOrigination  (0),
	emergencyCallRelease  (1), 
	mo-lr  (2),
	...,
	deferredmt-lrResponse  (3) ,
	deferredmo-lrTTTPInitiation  (4),
	emergencyCallHandover (5)  }
	--	deferredmt-lrResponse is applicable to the delivery of a location estimate 
	--	for an LDR initiated earlier by either the network (via an MT-LR activate deferred 
	--	location) or the UE (via a deferred MO-LR TTTP initiation)
	--	exception handling:
	--	a SubscriberLocationReport-Arg containing an unrecognized LCS-Event
	--	shall be rejected by a receiver with a return error cause of unexpected data value

--unused:TerminationCause ::= ENUMERATED {
--unused:	normal  (0),
--unused:	errorundefined  (1),
--unused:	internalTimeout  (2),
--unused:	congestion  (3),
--unused:	mt-lrRestart  (4),
--unused:	privacyViolation  (5),
--unused:	...,
--unused:	shapeOfLocationEstimateNotSupported (6) ,
--unused:	subscriberTermination (7),
--unused:	uETermination (8),
--unused:	networkTermination (9)  } 
-- mt-lrRestart shall be used to trigger the GMLC to restart the location procedure, 
-- either because the sending node knows that the terminal has moved under coverage 
-- of another MSC or SGSN (e.g. Send Identification received), or because the subscriber
-- has been deregistered due to a Cancel Location received from HLR.
--
-- exception handling
-- an unrecognized value shall be treated the same as value 1 (errorundefined) 

--unused:SequenceNumber ::= INTEGER (1..maxReportingAmount)

--unused:ServingNodeAddress ::= CHOICE {
--unused:	msc-Number	[0] ISDN-AddressString,
--unused:	sgsn-Number	[1] ISDN-AddressString,
--unused:	mme-Number	[2] DiameterIdentity }

--unused:SubscriberLocationReport-Res ::= SEQUENCE {
--unused:	extensionContainer	ExtensionContainer	OPTIONAL, 
--unused:	..., 
--unused:	na-ESRK		[0] ISDN-AddressString	OPTIONAL,
--unused:	na-ESRD		[1] ISDN-AddressString	OPTIONAL,
--unused:	h-gmlc-Address	[2]	GSN-Address	OPTIONAL,
--unused:	mo-lrShortCircuitIndicator	[3] NULL		OPTIONAL,
--unused:	reportingPLMNList	[4] ReportingPLMNList	OPTIONAL,
--unused:	lcs-ReferenceNumber	[5]	LCS-ReferenceNumber	OPTIONAL }

-- na-ESRK and na-ESRD are mutually exclusive
--
-- exception handling
-- receipt of both na-ESRK and na-ESRD shall be treated the same as a return error


END
