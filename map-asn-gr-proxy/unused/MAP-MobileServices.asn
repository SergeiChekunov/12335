-- $Id$
-- 3GPP TS 29.002 V10.4.0 (2011-09) 
-- 17.6.1    Mobile Service Operations

MAP-MobileServiceOperations {
   itu-t identified-organization (4) etsi (0) mobileDomain (0)
   gsm-Network (1) modules (3) map-MobileServiceOperations (5)
   version13 (13)}

DEFINITIONS IMPLICIT TAGS

::=

BEGIN

EXPORTS
    -- fault recovery operations
    ROS-reset,
    ROS-forwardCheckSS-Indication,
    ROS-restoreData
;

IMPORTS
    --unused: OPERATION
    --unused: FROM Remote-Operations-Information-Objects { joint-iso-itu-t remote-operations(4) informationObjects(5) version1(0)}

    systemFailure,
    dataMissing,
    unexpectedDataValue,
    unknownSubscriber

FROM MAP-Errors {
   itu-t identified-organization (4) etsi (0) mobileDomain (0)
   gsm-Network (1) modules (3) map-Errors (10) version13 (13)}


    ResetArg,
    RestoreDataArg,
    RestoreDataRes

FROM MAP-MS-DataTypes {
   itu-t identified-organization (4) etsi (0) mobileDomain (0)
   gsm-Network (1) modules (3) map-MS-DataTypes (11) version13 (13)}

    --unused: Invoke, ReturnResult, ReturnError, Reject, InvokeId, OperationCode
    --unused: FROM Remote-Operations-Generic-ROS-PDUs { joint-iso-itu-t remote-operations(4) generic-ROS-PDUs(6) version1(0)}

    ReturnError,
    Reject,
    InvokeIdType,
    MAP-OPERATION
FROM GSM-MAP {
   0 identified-organization (4) etsi (0) mobileDomain (0)
   gsm-Network (1) modules (3) map-Protocol (4) version5 (5) }
;

-- fault recovery operations

-- reset  OPERATION ::= { - -Timer m
--     ARGUMENT
--         ResetArg
--     CODE    local:37 }
ROS-reset ::=
  CHOICE {
    invoke              [1] IMPLICIT SEQUENCE {
      invokeId  InvokeIdType,
      linkedId  [0] InvokeIdType OPTIONAL,
      opcode-37 MAP-OPERATION,                       -- 37
      argument  ResetArg OPTIONAL                    -- ARGUMENT
    },
    reject              [4] IMPLICIT Reject
  }

-- forwardCheckSS-Indication  OPERATION ::= { - - Timer s
--     CODE    local:38 }
ROS-forwardCheckSS-Indication ::=
  CHOICE {
    invoke              [1] IMPLICIT SEQUENCE {
      invokeId  InvokeIdType,
      linkedId  [0] InvokeIdType OPTIONAL,
      opcode-38 MAP-OPERATION                        -- 38
    },
    reject              [4] IMPLICIT Reject
  }

-- restoreData  OPERATION ::= { - - Timer m
--     ARGUMENT
--         RestoreDataArg
--     RESULT
--         RestoreDataRes
--     ERRORS {
--         systemFailure |
--         dataMissing |
--         unexpectedDataValue |
--         unknownSubscriber}
--     CODE    local:57 }
ROS-restoreData ::=
  CHOICE {
    invoke              [1] IMPLICIT SEQUENCE {
      invokeId  InvokeIdType,
      linkedId  [0] InvokeIdType OPTIONAL,
      opcode-57 MAP-OPERATION,                       -- 57
      argument  RestoreDataArg OPTIONAL              -- ARGUMENT
    },
    returnResultLast    [2] IMPLICIT RestoreData-Result,
    returnError         [3] IMPLICIT ReturnError,    -- systemFailure|dataMissing|unexpectedDataValue|unknownSubscriber
    reject              [4] IMPLICIT Reject,
    returnResultNotLast [7] IMPLICIT RestoreData-Result
  }
RestoreData-Result ::= SEQUENCE {
    invokeId InvokeIdType,
    result SEQUENCE {
      opcode-57 MAP-OPERATION,                       -- 57
      result    RestoreDataRes                       -- RESULT
    } OPTIONAL
  }

END
