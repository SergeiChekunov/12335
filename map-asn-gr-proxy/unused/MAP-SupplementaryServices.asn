-- $Id$
-- 3GPP TS 29.002 V10.4.0 (2011-09)  
--17.6.4    Supplementary service operations

MAP-SupplementaryServiceOperations {
   itu-t identified-organization (4) etsi (0) mobileDomain (0)
   gsm-Network (1) modules (3) map-SupplementaryServiceOperations (8)
   version13 (13)}

DEFINITIONS IMPLICIT TAGS

::=

BEGIN

EXPORTS
    ROS-registerSS,
    ROS-eraseSS,
    ROS-activateSS,
    ROS-deactivateSS,
    ROS-interrogateSS,
    ROS-processUnstructuredSS-Request,
    ROS-unstructuredSS-Request,
    ROS-unstructuredSS-Notify,
    ROS-registerPassword,
    ROS-getPassword
    --,ROS-ss-InvocationNotification,
    --ROS-registerCC-Entry,
    --ROS-eraseCC-Entry
;

IMPORTS
    --unused: OPERATION
    --unused: FROM Remote-Operations-Information-Objects { joint-iso-itu-t remote-operations(4) informationObjects(5) version1(0)}

    systemFailure,
    dataMissing,
    unexpectedDataValue,
    unknownSubscriber,
    bearerServiceNotProvisioned,
    teleserviceNotProvisioned,
    callBarred,
    illegalSS-Operation,
    ss-ErrorStatus,
    ss-NotAvailable,
    ss-SubscriptionViolation,
    ss-Incompatibility,
    pw-RegistrationFailure,
    negativePW-Check,
    numberOfPW-AttemptsViolation,
    unknownAlphabet,
    ussd-Busy,
    absentSubscriber,
    illegalSubscriber,
    illegalEquipment,
    shortTermDenial,
    longTermDenial,
    facilityNotSupported
FROM MAP-Errors {
   itu-t identified-organization (4) etsi (0) mobileDomain (0)
   gsm-Network (1) modules (3) map-Errors (10) version13 (13)}

    RegisterSS-Arg,
    SS-Info,
    SS-ForBS-Code,
    InterrogateSS-Res,
    USSD-Arg,
    USSD-Res,
    Password,
    GuidanceInfo,
    SS-InvocationNotificationArg,
    SS-InvocationNotificationRes,
    RegisterCC-EntryArg,
    RegisterCC-EntryRes,
    EraseCC-EntryArg,
    EraseCC-EntryRes
FROM MAP-SS-DataTypes {
   itu-t identified-organization (4) etsi (0) mobileDomain (0)
   gsm-Network (1) modules (3) map-SS-DataTypes (14) version13 (13)}

    SS-Code
FROM MAP-SS-Code {
   itu-t identified-organization (4) etsi (0) mobileDomain (0)
   gsm-Network (1) modules (3) map-SS-Code (15) version13 (13)}

    --unused: Invoke, ReturnResult, ReturnError, Reject, InvokeId, OperationCode
    --unused: FROM Remote-Operations-Generic-ROS-PDUs { joint-iso-itu-t remote-operations(4) generic-ROS-PDUs(6) version1(0)}

    ReturnError,
    Reject,
    InvokeIdType,
    MAP-OPERATION
FROM GSM-MAP {
   0 identified-organization (4) etsi (0) mobileDomain (0)
   gsm-Network (1) modules (3) map-Protocol (4) version5 (5) }
;

-- supplementary service handling operations

-- registerSS  OPERATION ::= { - -Timer m
--     ARGUMENT
--         RegisterSS-Arg
--     RESULT
--         SS-Info
--         - - optional
--     ERRORS {
--         systemFailure |
--         dataMissing |
--         unexpectedDataValue |
--         bearerServiceNotProvisioned |
--         teleserviceNotProvisioned |
--         callBarred |
--         illegalSS-Operation |
--         ss-ErrorStatus |
--         ss-Incompatibility}
--     CODE    local:10 }
ROS-registerSS-Request ::=
  CHOICE {
    invoke              [1] IMPLICIT SEQUENCE {
      invokeId  InvokeIdType,
      linkedId  [0] InvokeIdType OPTIONAL,
      opcode-10 MAP-OPERATION,                       -- 10
      argument  RegisterSS-Arg OPTIONAL              -- ARGUMENT
    },
    returnResultLast    [2] IMPLICIT RegisterSS-Result,
    returnError         [3] IMPLICIT ReturnError,    -- systemFailure|dataMissing|unexpectedDataValue|bearerServiceNotProvisioned|teleserviceNotProvisioned|callBarred|illegalSS-Operation|ss-ErrorStatus|ss-Incompatibility
    reject              [4] IMPLICIT Reject,
    returnResultNotLast [7] IMPLICIT RegisterSS-Result
  }
RegisterSS-Result ::= SEQUENCE {
    invokeId InvokeIdType,
    result SEQUENCE {
      opcode-10 MAP-OPERATION,                       -- 10
      result    SS-Info                              -- RESULT
    } OPTIONAL
  }

-- eraseSS  OPERATION ::= { - -Timer m
--     ARGUMENT
--         SS-ForBS-Code
--     RESULT
--         SS-Info
--         - - optional
--     ERRORS {
--         systemFailure |
--         dataMissing |
--         unexpectedDataValue |
--         bearerServiceNotProvisioned |
--         teleserviceNotProvisioned |
--         callBarred |
--         illegalSS-Operation |
--         ss-ErrorStatus
--         }
--     CODE    local:11 }
ROS-eraseSS-Request ::=
  CHOICE {
    invoke              [1] IMPLICIT SEQUENCE {
      invokeId  InvokeIdType,
      linkedId  [0] InvokeIdType OPTIONAL,
      opcode-11 MAP-OPERATION,                       -- 11
      argument  SS-ForBS-Code OPTIONAL               -- ARGUMENT
    },
    returnResultLast    [2] IMPLICIT EraseSS-Result,
    returnError         [3] IMPLICIT ReturnError,    -- systemFailure|dataMissing|unexpectedDataValue|bearerServiceNotProvisioned|teleserviceNotProvisioned|
                                                     -- callBarred|illegalSS-Operation|ss-ErrorStatus
    reject              [4] IMPLICIT Reject,
    returnResultNotLast [7] IMPLICIT EraseSS-Result
  }
EraseSS-Result ::= SEQUENCE {
    invokeId InvokeIdType,
    result SEQUENCE {
      opcode-11 MAP-OPERATION,                       -- 11
      result    SS-Info                              -- RESULT
    } OPTIONAL
  }

-- activateSS  OPERATION ::= { - -Timer m
--     ARGUMENT
--         SS-ForBS-Code
--     RESULT
--         SS-Info
--         - - optional
--     ERRORS {
--         systemFailure |
--         dataMissing |
--         unexpectedDataValue |
--         bearerServiceNotProvisioned |
--         teleserviceNotProvisioned |
--         callBarred |
--         illegalSS-Operation |
--         ss-ErrorStatus |
--         ss-SubscriptionViolation |
--         ss-Incompatibility |
--         negativePW-Check |
--         numberOfPW-AttemptsViolation}
--     CODE    local:12 }
ROS-activateSS-Request ::=
  CHOICE {
    invoke              [1] IMPLICIT SEQUENCE {
      invokeId  InvokeIdType,
      linkedId  [0] InvokeIdType OPTIONAL,
      opcode-12 MAP-OPERATION,                       -- 12
      argument  SS-ForBS-Code OPTIONAL               -- ARGUMENT
    },
    returnResultLast    [2] IMPLICIT ActivateSS-Result,
    returnError         [3] IMPLICIT ReturnError,    -- systemFailure|dataMissing|unexpectedDataValue|bearerServiceNotProvisioned|teleserviceNotProvisioned|
                                                     -- callBarred|illegalSS-Operation|ss-ErrorStatus|ss-SubscriptionViolation|ss-Incompatibility|
                                                     -- negativePW-Check|numberOfPW-AttemptsViolation
    reject              [4] IMPLICIT Reject,
    returnResultNotLast [7] IMPLICIT ActivateSS-Result
  }
ActivateSS-Result ::= SEQUENCE {
    invokeId InvokeIdType,
    result SEQUENCE {
      opcode-12 MAP-OPERATION,                       -- 12
      result    SS-Info                              -- RESULT
    } OPTIONAL
  }

-- deactivateSS  OPERATION ::= { - -Timer m
--     ARGUMENT
--         SS-ForBS-Code
--     RESULT
--         SS-Info
--         - - optional
--     ERRORS {
--         systemFailure |
--         dataMissing |
--         unexpectedDataValue |
--         bearerServiceNotProvisioned |
--         teleserviceNotProvisioned |
--         callBarred |
--         illegalSS-Operation |
--         ss-ErrorStatus |
--         ss-SubscriptionViolation |
--         negativePW-Check |
--         numberOfPW-AttemptsViolation}
--     CODE    local:13 }
ROS-deactivateSS-Request ::=
  CHOICE {
    invoke              [1] IMPLICIT SEQUENCE {
      invokeId  InvokeIdType,
      linkedId  [0] InvokeIdType OPTIONAL,
      opcode-13 MAP-OPERATION,                       -- 13
      argument  SS-ForBS-Code OPTIONAL               -- ARGUMENT
    },
    returnResultLast    [2] IMPLICIT DeactivateSS-Result,
    returnError         [3] IMPLICIT ReturnError,    -- systemFailure|dataMissing|unexpectedDataValue|bearerServiceNotProvisioned|teleserviceNotProvisioned|
                                                     -- callBarred|illegalSS-Operation|ss-ErrorStatus|ss-SubscriptionViolation|negativePW-Check|
                                                     -- numberOfPW-AttemptsViolation
    reject              [4] IMPLICIT Reject,
    returnResultNotLast [7] IMPLICIT DeactivateSS-Result
  }
DeactivateSS-Result ::= SEQUENCE {
    invokeId InvokeIdType,
    result SEQUENCE {
      opcode-13 MAP-OPERATION,                       -- 13
      result    SS-Info                              -- RESULT
    } OPTIONAL
  }

-- interrogateSS  OPERATION ::= { - -Timer m
--     ARGUMENT
--         SS-ForBS-Code
--     RESULT
--         InterrogateSS-Res
--     ERRORS {
--         systemFailure |
--         dataMissing |
--         unexpectedDataValue |
--         bearerServiceNotProvisioned |
--         teleserviceNotProvisioned |
--         callBarred |
--         illegalSS-Operation |
--         ss-NotAvailable}
--     CODE    local:14 }
ROS-interrogateSS-Request ::=
  CHOICE {
    invoke              [1] IMPLICIT SEQUENCE {
      invokeId  InvokeIdType,
      linkedId  [0] InvokeIdType OPTIONAL,
      opcode-14 MAP-OPERATION,                       -- 14
      argument  SS-ForBS-Code OPTIONAL               -- ARGUMENT
    },
    returnResultLast    [2] IMPLICIT InterrogateSS-Result,
    returnError         [3] IMPLICIT ReturnError,    -- systemFailure|dataMissing|unexpectedDataValue|bearerServiceNotProvisioned|teleserviceNotProvisioned|
                                                     -- callBarred|illegalSS-Operation|ss-NotAvailable
    reject              [4] IMPLICIT Reject,
    returnResultNotLast [7] IMPLICIT InterrogateSS-Result
  }
InterrogateSS-Result ::= SEQUENCE {
    invokeId InvokeIdType,
    result SEQUENCE {
      opcode-14 MAP-OPERATION,                       -- 14
      result    InterrogateSS-Res                    -- RESULT
    } OPTIONAL
  }

-- processUnstructuredSS-Request  OPERATION ::= { - -Timer 10 minutes
--     ARGUMENT
--         USSD-Arg
--     RESULT
--         USSD-Res
--     ERRORS {
--         systemFailure |
--         dataMissing |
--         unexpectedDataValue |
--         unknownAlphabet |
--         callBarred}
--     CODE    local:59 }
ROS-processUnstructuredSS-Request ::=
  CHOICE {
    invoke              [1] IMPLICIT SEQUENCE {
      invokeId  InvokeIdType,
      linkedId  [0] InvokeIdType OPTIONAL,
      opcode-59 MAP-OPERATION,                       -- 59
      argument  USSD-Arg OPTIONAL                    -- ARGUMENT
    },
    returnResultLast    [2] IMPLICIT ProcessUnstructuredSS-Request-Result,
    returnError         [3] IMPLICIT ReturnError,    -- systemFailure|dataMissing|unexpectedDataValue|unknownAlphabet|callBarred
    reject              [4] IMPLICIT Reject,
    returnResultNotLast [7] IMPLICIT ProcessUnstructuredSS-Request-Result
  }
ProcessUnstructuredSS-Request-Result ::= SEQUENCE {
    invokeId InvokeIdType,
    result SEQUENCE {
      opcode-59 MAP-OPERATION,                       -- 59
      result    USSD-Res                             -- RESULT
    } OPTIONAL
  }

--unstructuredSS-Request  OPERATION ::= { - -Timer ml
--    ARGUMENT
--        USSD-Arg
--    RESULT
--        USSD-Res
--        - - optional
--    ERRORS {
--        systemFailure |
--        dataMissing |
--        unexpectedDataValue |
--        absentSubscriber |
--        illegalSubscriber |
--        illegalEquipment |
--        unknownAlphabet |
--        ussd-Busy}
--    CODE    local:60 }
ROS-unstructuredSS-Request ::=
  CHOICE {
    invoke              [1] IMPLICIT SEQUENCE {
      invokeId  InvokeIdType,
      linkedId  [0] InvokeIdType OPTIONAL,
      opcode-60 MAP-OPERATION,                       -- 60
      argument  USSD-Arg OPTIONAL                    -- ARGUMENT
    },
    returnResultLast    [2] IMPLICIT UnstructuredSS-Request-Result,
    returnError         [3] IMPLICIT ReturnError,    -- systemFailure|dataMissing|unexpectedDataValue|absentSubscriber|illegalSubscriber|illegalEquipment|
                                                     -- unknownAlphabet|ussd-Busy
    reject              [4] IMPLICIT Reject,
    returnResultNotLast [7] IMPLICIT UnstructuredSS-Request-Result
  }
UnstructuredSS-Request-Result ::= SEQUENCE {
    invokeId InvokeIdType,
    result   SEQUENCE {
      opcode-60 MAP-OPERATION,                       -- 60
      result    USSD-Res                             -- RESULT
    } OPTIONAL
  }

--unstructuredSS-Notify  OPERATION ::= {                - -Timer ml
--    ARGUMENT
--        USSD-Arg
--    RETURN RESULT TRUE
--    ERRORS {
--        systemFailure |
--        dataMissing |
--        unexpectedDataValue |
--        absentSubscriber |
--        illegalSubscriber |
--        illegalEquipment |
--        unknownAlphabet |
--        ussd-Busy}
--    CODE    local:61 }
ROS-unstructuredSS-Notify ::=
  CHOICE {
    invoke              [1] IMPLICIT SEQUENCE {
      invokeId  InvokeIdType,
      linkedId  [0] InvokeIdType OPTIONAL,
      opcode-61 MAP-OPERATION,                       -- 61
      argument  USSD-Arg OPTIONAL                    -- ARGUMENT
    },
    returnResultLast    [2] IMPLICIT UnstructuredSS-Notify-Result,
    returnError         [3] IMPLICIT ReturnError,    -- systemFailure|dataMissing|unexpectedDataValue|absentSubscriber|illegalSubscriber|illegalEquipment|
                                                     -- unknownAlphabet|ussd-Busy
    reject              [4] IMPLICIT Reject,
    returnResultNotLast [7] IMPLICIT UnstructuredSS-Notify-Result
  }
UnstructuredSS-Notify-Result ::= SEQUENCE {
    invokeId InvokeIdType,
    result   SEQUENCE {
      opcode-61 MAP-OPERATION,                       -- 61
      result    BOOLEAN DEFAULT TRUE                 -- RESULT
    } OPTIONAL
  }

--registerPassword  OPERATION ::= { - -Timer ml
--    ARGUMENT
--        SS-Code
--    RESULT
--        Password
--    ERRORS {
--        systemFailure |
--        dataMissing |
--        unexpectedDataValue |
--        callBarred |
--        ss-SubscriptionViolation |
--        pw-RegistrationFailure |
--        negativePW-Check |
--        numberOfPW-AttemptsViolation}
--    LINKED {
--        getPassword}
--    CODE    local:17 }
ROS-registerPassword ::=
  CHOICE {
    invoke              [1] IMPLICIT SEQUENCE {
      invokeId  InvokeIdType,
      linkedId  [0] InvokeIdType OPTIONAL,
      opcode-17 MAP-OPERATION,                       -- 17
      argument  SS-Code OPTIONAL                     -- ARGUMENT
    },
    returnResultLast    [2] IMPLICIT RegisterPassword-Result,
    returnError         [3] IMPLICIT ReturnError,    -- systemFailure|dataMissing|unexpectedDataValue|callBarred|ss-SubscriptionViolation|
                                                     -- pw-RegistrationFailure|negativePW-Check|numberOfPW-AttemptsViolation
    reject              [4] IMPLICIT Reject,
    returnResultNotLast [7] IMPLICIT RegisterPassword-Result
  }
RegisterPassword-Result ::= SEQUENCE {
    invokeId InvokeIdType,
    result   SEQUENCE {
      opcode-17 MAP-OPERATION,                       -- 17
      result    Password                             -- RESULT
    } OPTIONAL
  }

--getPassword  OPERATION ::= { - -Timer m
--    ARGUMENT
--        GuidanceInfo
--    RESULT
--        Password
--    CODE    local:18 }
ROS-getPassword ::=
  CHOICE {
    invoke              [1] IMPLICIT SEQUENCE {
      invokeId  InvokeIdType,
      linkedId  [0] InvokeIdType OPTIONAL,
      opcode-18 MAP-OPERATION,                       -- 18
      argument  GuidanceInfo OPTIONAL                -- ARGUMENT
    },
    returnResultLast    [2] IMPLICIT GetPassword-Result,
    returnError         [3] IMPLICIT ReturnError,
    reject              [4] IMPLICIT Reject,
    returnResultNotLast [7] IMPLICIT GetPassword-Result
  }
GetPassword-Result ::= SEQUENCE {
    invokeId InvokeIdType,
    result   SEQUENCE {
      opcode-18 MAP-OPERATION,                       -- 18
      result    Password                             -- RESULT
    } OPTIONAL
  }

--ss-InvocationNotification  OPERATION ::= { - -Timer m
--    ARGUMENT
--        SS-InvocationNotificationArg
--    RESULT
--        SS-InvocationNotificationRes
--        - - optional
--    ERRORS {
--        dataMissing |
--        unexpectedDataValue |
--        unknownSubscriber}
--    CODE    local:72 }

--registerCC-Entry  OPERATION ::= { - -Timer m
--    ARGUMENT
--        RegisterCC-EntryArg
--    RESULT
--        RegisterCC-EntryRes
--    ERRORS {
--        systemFailure |
--        dataMissing |
--        unexpectedDataValue |
--        callBarred |
--        illegalSS-Operation |
--        ss-ErrorStatus |
--        ss-Incompatibility |
--        shortTermDenial |
--        longTermDenial |
--        facilityNotSupported}
--    CODE    local:76 }

--eraseCC-Entry  OPERATION ::= { - -Timer m
--    ARGUMENT
--        EraseCC-EntryArg
--    RESULT
--        EraseCC-EntryRes
--    ERRORS {
--        systemFailure |
--        dataMissing |
--        unexpectedDataValue |
--        callBarred |
--        illegalSS-Operation |
--        ss-ErrorStatus}
--    CODE    local:77 }

END
