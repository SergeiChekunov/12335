-- $Id$
--
-- Taken from 3GPP TS 29.002 V10.4.0 (2011-09)
--
--17.7.12	Group Call data types
 
MAP-GR-DataTypes {
   itu-t identified-organization (4) etsi (0) mobileDomain (0)
   gsm-Network (1) modules (3) map-GR-DataTypes (23) version13 (13)}

DEFINITIONS

IMPLICIT TAGS

::=

BEGIN

EXPORTS
	--unused:PrepareGroupCallArg,
	--unused:PrepareGroupCallRes,
	SendGroupCallEndSignalArg,
	--unused:SendGroupCallEndSignalRes,
	ForwardGroupCallSignallingArg,
	--unused:ProcessGroupCallSignallingArg,
	SendGroupCallInfoArg,
	SendGroupCallInfoRes
;

IMPORTS
	ISDN-AddressString,
	IMSI, 
	--unused:TMSI,
	--unused:EMLPP-Priority,
	ASCI-CallReference,
	--unused:SignalInfo,
	GlobalCellId--unused:,
	--unused:AccessNetworkSignalInfo
FROM MAP-CommonDataTypes {
   itu-t identified-organization (4) etsi (0) mobileDomain (0)
   gsm-Network (1) modules (3) map-CommonDataTypes (18) version13 (13)}

	Ext-TeleserviceCode
FROM MAP-TS-Code {
   itu-t identified-organization (4) etsi (0) mobileDomain (0)
   gsm-Network (1) modules (3) map-TS-Code (19) version13 (13)}

	--unused:Kc,
	--unused:AdditionalInfo,
	--unused:GroupId,
	Long-GroupId,
	AdditionalSubscriptions--unused:,
	--unused:Cksn
FROM MAP-MS-DataTypes {
   itu-t identified-organization (4) etsi (0) mobileDomain (0)
   gsm-Network (1) modules (3) map-MS-DataTypes (11) version13 (13)}

--unused:	ExtensionContainer
--unused:FROM MAP-ExtensionDataTypes {
--unused:   itu-t identified-organization (4) etsi (0) mobileDomain (0)
--unused:   gsm-Network (1) modules (3) map-ExtensionDataTypes (21) version13 (13)}
;


--unused:PrepareGroupCallArg ::= SEQUENCE {
--unused:	teleservice	Ext-TeleserviceCode,
--unused:	asciCallReference	ASCI-CallReference,
--unused:	codec-Info	CODEC-Info,
--unused:	cipheringAlgorithm	CipheringAlgorithm,
--unused:	groupKeyNumber-Vk-Id	[0] GroupKeyNumber	OPTIONAL,
--unused:	groupKey		[1] Kc		OPTIONAL, 
--unused:	- - this parameter shall not be sent and shall be discarded if received
--unused:	priority		[2] EMLPP-Priority	OPTIONAL,
--unused:	uplinkFree	[3] NULL		OPTIONAL,
--unused:	extensionContainer	[4] ExtensionContainer	OPTIONAL,
--unused:	...,
--unused:	vstk			[5] VSTK		OPTIONAL,
--unused:	vstk-rand		[6] VSTK-RAND	OPTIONAL,
--unused:	talkerChannelParameter	[7] NULL		OPTIONAL,
--unused:	uplinkReplyIndicator	[8] NULL		OPTIONAL}

--unused:VSTK ::= OCTET STRING (SIZE (16))

--unused:VSTK-RAND ::= OCTET STRING (SIZE (5))
	-- The 36 bit value is carried in bit 7 of octet 1 to bit 4 of octet 5
	-- bits 3, 2, 1, and 0 of octet 5 are padded with zeros.

--unused:PrepareGroupCallRes ::= SEQUENCE {
--unused:	groupCallNumber	ISDN-AddressString,
--unused:	extensionContainer	ExtensionContainer	OPTIONAL,
--unused:	...}

SendGroupCallEndSignalArg ::= SEQUENCE {
	imsi			IMSI			OPTIONAL,
	--unused:extensionContainer	ExtensionContainer	OPTIONAL,
	...--unused:,
	--unused:talkerPriority	[0]TalkerPriority	OPTIONAL,
	--unused:additionalInfo	[1]AdditionalInfo	OPTIONAL-- }

--unused:TalkerPriority ::= ENUMERATED {
--unused:	normal  (0),
--unused:	privileged  (1),
--unused:	emergency  (2)}

--unused:SendGroupCallEndSignalRes ::= SEQUENCE {
--unused:	extensionContainer	ExtensionContainer	OPTIONAL,
--unused:	...}

ForwardGroupCallSignallingArg ::= SEQUENCE {
	imsi			IMSI			OPTIONAL,
	--unused:uplinkRequestAck	[0] NULL		OPTIONAL,
	--unused:uplinkReleaseIndication	[1] NULL		OPTIONAL,
	--unused:uplinkRejectCommand	[2] NULL		OPTIONAL,
	--unused:uplinkSeizedCommand	[3] NULL		OPTIONAL,
	--unused:uplinkReleaseCommand	[4] NULL		OPTIONAL,
	--unused:extensionContainer	ExtensionContainer	OPTIONAL,
	...--unused:, 
	--unused:stateAttributes	[5] StateAttributes	OPTIONAL,
	--unused:talkerPriority	[6] TalkerPriority	OPTIONAL,
	--unused:additionalInfo	[7] AdditionalInfo	OPTIONAL,
	--unused:emergencyModeResetCommandFlag	[8] NULL		OPTIONAL,
	--unused:sm-RP-UI		[9] SignalInfo	OPTIONAL,
	--unused:an-APDU	[10] AccessNetworkSignalInfo	OPTIONAL
 }

--unused:ProcessGroupCallSignallingArg ::= SEQUENCE {
--unused:	uplinkRequest	[0] NULL		OPTIONAL,
--unused:	uplinkReleaseIndication	[1] NULL		OPTIONAL,
--unused:	releaseGroupCall	[2] NULL		OPTIONAL,
--unused:	extensionContainer	ExtensionContainer	OPTIONAL,
--unused:	...,
--unused:	talkerPriority	[3] TalkerPriority	OPTIONAL,
--unused:	additionalInfo	[4] AdditionalInfo	OPTIONAL,
--unused:	emergencyModeResetCommandFlag	[5] NULL		OPTIONAL,
--unused:	an-APDU	[6] AccessNetworkSignalInfo	OPTIONAL }

--unused:GroupKeyNumber ::= INTEGER (0..15)

--unused:CODEC-Info ::= OCTET STRING (SIZE (5..10))
	-- Refers to channel type
	-- coded according to 3GPP TS 48.008 [49] and including Element identifier and Length	

--unused:CipheringAlgorithm ::= OCTET STRING (SIZE (1))
	-- Refers to 'permitted algorithms' in 'encryption information'
	-- coded according to 3GPP TS 48.008 [49]:
	
	-- Bits 8-1 
	-- 8765 4321
	-- 0000 0001	No encryption
	-- 0000 0010	GSM A5/1
	-- 0000 0100	GSM A5/2
	-- 0000 1000	GSM A5/3
	-- 0001 0000	GSM A5/4
	-- 0010 0000	GSM A5/5
	-- 0100 0000	GSM A5/6
	-- 1000 0000	GSM A5/7

--unused:StateAttributes ::= SEQUENCE {
--unused:	downlinkAttached			[5] NULL		OPTIONAL,
--unused:	uplinkAttached			[6] NULL		OPTIONAL,
--unused:	dualCommunication			[7] NULL		OPTIONAL,
--unused:	callOriginator			[8] NULL		OPTIONAL }

	-- Refers to 3GPP TS 44.068 for definitions of StateAttributes fields. 


SendGroupCallInfoArg ::= SEQUENCE {
	requestedInfo	RequestedInfoGR,          --unused
	groupId		Long-GroupId,                 --unused
	teleservice	Ext-TeleserviceCode,          --unused
	cellId		[0] GlobalCellId	OPTIONAL, --unused
	imsi			[1] IMSI		OPTIONAL,
	--unused:tmsi			[2] TMSI		OPTIONAL,
	--unused:additionalInfo	[3] AdditionalInfo	OPTIONAL,
	--unused:talkerPriority	[4] TalkerPriority	OPTIONAL,
	--unused:cksn			[5] Cksn		OPTIONAL,
	--unused:extensionContainer	[6] ExtensionContainer	OPTIONAL,
	... }

RequestedInfoGR ::= ENUMERATED {
	anchorMSC-AddressAndASCI-CallReference			(0),
	imsiAndAdditionalInfoAndAdditionalSubscription		(1),
	... }
--	exception handling:
--	an unrecognized value shall be rejected by the receiver with a return error cause of 
--	unexpected data value

SendGroupCallInfoRes ::= SEQUENCE {
	anchorMSC-Address	[0] ISDN-AddressString	OPTIONAL,  --unused
	asciCallReference	[1] ASCI-CallReference	OPTIONAL,  --unused
	imsi			[2] IMSI		OPTIONAL,
	--unused:additionalInfo	[3] AdditionalInfo	OPTIONAL,
	--unused:additionalSubscriptions	[4] AdditionalSubscriptions	OPTIONAL,
	--unused:kc			[5] Kc		OPTIONAL,
	--unused:extensionContainer	[6] ExtensionContainer	OPTIONAL,
	... }


END
