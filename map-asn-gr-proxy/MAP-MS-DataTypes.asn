-- ETSI TS 129 002 V10.4.0 (2011-10)
-- 17.7.1 Mobile Service data types

MAP-MS-DataTypes {
    itu-t identified-organization (4) etsi (0) mobileDomain (0)
    gsm-Network (1) modules (3) map-MS-DataTypes (11) version13 (13)}

DEFINITIONS IMPLICIT TAGS ::=

BEGIN

EXPORTS
    -- location registration types
    --unused:UpdateLocationArg,
    --unused:UpdateLocationRes,
    --unused:CancelLocationArg,
    --unused:CancelLocationRes,
    --unused:PurgeMS-Arg,
    --unused:PurgeMS-Res,
    --unused:SendIdentificationArg,
    --unused:SendIdentificationRes,
    --unused:UpdateGprsLocationArg,
    --unused:UpdateGprsLocationRes,
    --unused:IST-SupportIndicator,
    --unused:SupportedLCS-CapabilitySets,

    -- handover types
    --unused:ForwardAccessSignalling-Arg,
    --unused:PrepareHO-Arg,
    --unused:PrepareHO-Res,
    --unused:PrepareSubsequentHO-Arg,
    --unused:PrepareSubsequentHO-Res,
    --unused:ProcessAccessSignalling-Arg,
    --unused:SendEndSignal-Arg,
    --unused:SendEndSignal-Res,

    -- authentication management types
    --unused:SendAuthenticationInfoArg,
    --unused:SendAuthenticationInfoRes,
    --unused:AuthenticationFailureReportArg,
    --unused:AuthenticationFailureReportRes,

    -- security management types
    RAND,
    SRES,
    Kc, 
	--unused:Cksn,
    --unused:AuthenticationTripletV1,- -unused:TripletList,

    -- equipment management types
    --unused:CheckIMEI-Arg,
    --unused:CheckIMEI-Res,

    -- subscriber management types
    --unused:SubscriberData, - -unused:InsertSubscriberDataArg,
    --unused:InsertSubscriberDataRes,
    --unused:LSAIdentity,
    --unused:DeleteSubscriberDataArg,
    --unused:DeleteSubscriberDataRes,
    --unused:Ext-QoS-Subscribed,
    --unused:Ext2-QoS-Subscribed,
    --unused:Ext3-QoS-Subscribed,
    --unused:Ext4-QoS-Subscribed,
    --unused:AuthenticationSetList,
    --unused:ODB-Data,
    --unused:SubscriberStatus,
    --unused:ZoneCodeList,
    --unused:maxNumOfZoneCodes,
    O-CSI,
    D-CSI,
    O-BcsmCamelTDPCriteriaList,
    T-BCSM-CAMEL-TDP-CriteriaList,
    --unused:SS-CSI,
    --unused:ServiceKey,
    --unused:DefaultCallHandling,
    --unused:CamelCapabilityHandling,
    --unused:BasicServiceCriteria,
    SupportedCamelPhases,
    OfferedCamel4CSIs,
    --unused:OfferedCamel4Functionalities,
    --unused:maxNumOfCamelTDPData,
    --unused:CUG-Index,
    --unused:CUG-Info,
    CUG-Interlock,
    --unused:InterCUG-Restrictions,
    --unused:IntraCUG-Options,
    --unused:NotificationToMSUser,
    --unused:QoS-Subscribed,
    IST-AlertTimerValue,
    T-CSI,
    --unused:T-BcsmTriggerDetectionPoint,
    APN,
    --unused:AdditionalInfo,
    Category,

    -- fault recovery types
    --unused:ResetArg,
    --unused:RestoreDataArg,
    --unused:RestoreDataRes,

    -- provide subscriber info types
    --unused:GeographicalInformation,
    --unused:MS-Classmark2,
    --unused:GPRSMSClass,

    -- subscriber information enquiry types
    --unused:ProvideSubscriberInfoArg,
    --unused:ProvideSubscriberInfoRes,
    SubscriberInfo,
    --unused:LocationInformation,
    --unused:LocationInformationGPRS,
    --unused:SubscriberState,
    --unused:GPRSChargingID,
    --unused:MNPInfoRes,
    --unused:RouteingNumber,

    -- any time information enquiry types
    --unused:AnyTimeInterrogationArg,
    --unused:AnyTimeInterrogationRes,

    -- any time information handling types
    --unused:AnyTimeSubscriptionInterrogationArg,
    --unused:AnyTimeSubscriptionInterrogationRes,
    --unused:AnyTimeModificationArg,
    --unused:AnyTimeModificationRes,

    -- subscriber data modification notification types
    --unused:NoteSubscriberDataModifiedArg,
    --unused:NoteSubscriberDataModifiedRes,

    -- gprs location information retrieval types
    --unused:SendRoutingInfoForGprsArg,
    --unused:SendRoutingInfoForGprsRes,

    -- failure reporting types
    --unused:FailureReportArg,
    --unused:FailureReportRes,

    -- gprs notification types
    --unused:NoteMsPresentForGprsArg,
    --unused:NoteMsPresentForGprsRes,

    -- Mobility Management types
    --unused:NoteMM-EventArg,
    --unused:NoteMM-EventRes,
    NumberPortabilityStatus,
    --unused:PagingArea,

    -- VGCS / VBS types types
    --unused:GroupId,
    Long-GroupId--unused:,
    --unused:AdditionalSubscriptions
    ;

IMPORTS
    maxNumOfSS,
    SS-SubscriptionOption,
    SS-List,
    SS-ForBS-Code,
    Password--unused:,
    --unused:OverrideCategory,
    --unused:CliRestrictionOption
FROM MAP-SS-DataTypes {
    itu-t identified-organization (4) etsi (0) mobileDomain (0)
    gsm-Network (1) modules (3) map-SS-DataTypes (14) version13 (13)}

    SS-Code
FROM MAP-SS-Code {
    itu-t identified-organization (4) etsi (0) mobileDomain (0)
    gsm-Network (1) modules (3) map-SS-Code (15) version13 (13)}

    Ext-BearerServiceCode
FROM MAP-BS-Code {
    itu-t identified-organization (4) etsi (0) mobileDomain (0)
    gsm-Network (1) modules (3) map-BS-Code (20) version13 (13)}

    Ext-TeleserviceCode
FROM MAP-TS-Code {
    itu-t identified-organization (4) etsi (0) mobileDomain (0)
    gsm-Network (1) modules (3) map-TS-Code (19) version13 (13)}

    AddressString,
    ISDN-AddressString,
    ISDN-SubaddressString,
    FTN-AddressString,
    AccessNetworkSignalInfo,
    IMSI,
    IMEI,
    TMSI,
    --unused:HLR-List,
    LMSI,
    Identity,
    GlobalCellId,
    CellGlobalIdOrServiceAreaIdOrLAI,
    Ext-BasicServiceCode,
    --unused:NAEA-PreferredCI,
    EMLPP-Info,
    --unused:MC-SS-Info,
    SubscriberIdentity,
    AgeOfLocationInformation,
    LCSClientExternalID,
    LCSClientInternalID,
    Ext-SS-Status,
    LCSServiceTypeID,
    ASCI-CallReference,
    TBCD-STRING,
    LAIFixedLength,
    PLMN-Id,
    --unused:EMLPP-Priority,
    GSN-Address,
    DiameterIdentity,
    Time,
    E-UTRAN-CGI,
    TA-Id,
    RAIdentity
FROM MAP-CommonDataTypes {
    itu-t identified-organization (4) etsi (0) mobileDomain (0)
    gsm-Network (1) modules (3) map-CommonDataTypes (18) version13 (13)}

    ExtensionContainer
FROM MAP-ExtensionDataTypes {
    itu-t identified-organization (4) etsi (0) mobileDomain (0)
    gsm-Network (1) modules (3) map-ExtensionDataTypes (21) version13 (13)}

    AbsentSubscriberDiagnosticSM
FROM MAP-ER-DataTypes {
    itu-t identified-organization (4) etsi (0) mobileDomain (0)
    gsm-Network (1) modules (3) map-ER-DataTypes (17) version13 (13)}

--unused:    TracePropagationList
--unused:FROM MAP-OM-DataTypes {
--unused:    itu-t identified-organization (4) etsi (0) mobileDomain (0)
--unused:    gsm-Network (1) modules (3) map-OM-DataTypes (12) version13 (13)}
    ;

-- location registration types
UpdateLocationArg ::= SEQUENCE {
    imsi IMSI,
    msc-Number [1] ISDN-AddressString,
    vlr-Number ISDN-AddressString,
    lmsi [10] LMSI OPTIONAL,                        --unused
    extensionContainer ExtensionContainer OPTIONAL, --unused
    ... ,
    vlr-Capability [6] VLR-Capability OPTIONAL,     --unused
    informPreviousNetworkEntity [11] NULL OPTIONAL, --unused
    cs-LCS-NotSupportedByUE [12] NULL OPTIONAL,     --unused
    v-gmlc-Address [2] GSN-Address OPTIONAL,        --unused
    add-info [13] ADD-Info OPTIONAL,                ...
    --unused:pagingArea [14] PagingArea OPTIONAL,
    --unused:skipSubscriberDataUpdate [15] NULL OPTIONAL,
    --unused:- - The skipSubscriberDataUpdate parameter in the UpdateLocationArg and the ADD-Info
    --unused:- - structures carry the same semantic.
    --unused:restorationIndicator [16] NULL OPTIONAL
    }

VLR-Capability ::= SEQUENCE {
    supportedCamelPhases [0] SupportedCamelPhases OPTIONAL,
    extensionContainer ExtensionContainer OPTIONAL,
    ... ,
    solsaSupportIndicator [2] NULL OPTIONAL,
    istSupportIndicator [1] IST-SupportIndicator OPTIONAL,
    superChargerSupportedInServingNetworkEntity [3] SuperChargerInfo OPTIONAL,
    longFTN-Supported [4] NULL OPTIONAL,
    supportedLCS-CapabilitySets [5] SupportedLCS-CapabilitySets OPTIONAL,
    offeredCamel4CSIs [6] OfferedCamel4CSIs OPTIONAL,
    supportedRAT-TypesIndicator [7] SupportedRAT-Types OPTIONAL,
    longGroupID-Supported [8] NULL OPTIONAL,
    mtRoamingForwardingSupported [9] NULL OPTIONAL }

SupportedRAT-Types ::= BIT STRING {
    utran (0),
    geran (1),
    gan (2),
    i-hspa-evolution (3),
    e-utran (4)} (SIZE (2..8))
    -- exception handling: bits 5 to 7 shall be ignored if received and not understood

SuperChargerInfo ::= CHOICE {
    sendSubscriberData [0] NULL,
    subscriberDataStored [1] AgeIndicator }

AgeIndicator ::= OCTET STRING (SIZE (1..6))
   -- The internal structure of this parameter is implementation specific.

IST-SupportIndicator ::= ENUMERATED {
    basicISTSupported (0),
    istCommandSupported (1),
    ...}
    -- exception handling:
    -- reception of values > 1 shall be mapped to ' istCommandSupported '

SupportedLCS-CapabilitySets ::= BIT STRING {
    lcsCapabilitySet1 (0),
    lcsCapabilitySet2 (1),
    lcsCapabilitySet3 (2),
    lcsCapabilitySet4 (3) ,
    lcsCapabilitySet5 (4) } (SIZE (2..16))
    -- Core network signalling capability set1 indicates LCS Release98 or Release99 version.
    -- Core network signalling capability set2 indicates LCS Release4.
    -- Core network signalling capability set3 indicates LCS Release5.
    -- Core network signalling capability set4 indicates LCS Release6.
    -- Core network signalling capability set5 indicates LCS Release7 or later version.
    -- A node shall mark in the BIT STRING all LCS capability sets it supports.
    -- If no bit is set then the sending node does not support LCS.
    -- If the parameter is not sent by an VLR then the VLR may support at most capability set1.
    -- If the parameter is not sent by an SGSN then no support for LCS is assumed.
    -- An SGSN is not allowed to indicate support of capability set1.
    -- Other bits than listed above shall be discarded.

--* UpdateLocationRes ::= SEQUENCE {
--     hlr-Number ISDN-AddressString,
--     extensionContainer ExtensionContainer OPTIONAL,
--     ...,
--     add-Capability NULL OPTIONAL,
--     pagingArea-Capability [0]NULL OPTIONAL }

UpdateLocationRes ::= CHOICE {
	data [UNIVERSAL 16] SEQUENCE {
    	hlr-Number ISDN-AddressString,
    	extensionContainer ExtensionContainer OPTIONAL,
    	... --unused:,
    	--unused:add-Capability NULL OPTIONAL,
    	--unused:pagingArea-Capability [0]NULL OPTIONAL
    },
	hlr-Number [UNIVERSAL 4] ISDN-AddressString
}

ADD-Info ::= SEQUENCE {
    imeisv [0] IMEI ,
    skipSubscriberDataUpdate [1] NULL OPTIONAL,
    -- The skipSubscriberDataUpdate parameter in the UpdateLocationArg and the ADD-Info
    -- structures carry the same semantic.
    ...}

--unused:PagingArea ::= SEQUENCE SIZE (1..5) OF LocationArea

--unused:LocationArea ::= CHOICE {
--unused:    laiFixedLength [0] LAIFixedLength,
--unused:    lac [1] LAC}

--unused:LAC ::= OCTET STRING (SIZE (2))
    -- Refers to Location Area Code of the Location Area Identification defined in
    -- 3GPP TS 23.003 [17].
    -- Location Area Code according to 3GPP TS 24.008 [35]

--* CancelLocationArg ::= [3] SEQUENCE {
--     identity Identity,
--     cancellationType CancellationType OPTIONAL,
--     extensionContainer ExtensionContainer OPTIONAL,
--     ...,
--     typeOfUpdate [0] TypeOfUpdate OPTIONAL,
--     mtrf-SupportedAndAuthorized [1] NULL OPTIONAL,
--     mtrf-SupportedAndNotAuthorized [2] NULL OPTIONAL,
--     newMSC-Number [3] ISDN-AddressString OPTIONAL,
--     newVLR-Number [4] ISDN-AddressString OPTIONAL,
--     new-lmsi [5] LMSI OPTIONAL
--     }
     -- mtrf-SupportedAndAuthorized and mtrf-SupportedAndNotAuthorized shall not
     -- both be present

CancelLocationArg ::= CHOICE {
	data-v2 [3] SEQUENCE {
    	identity Identity,
    	cancellationType CancellationType OPTIONAL,
    	extensionContainer ExtensionContainer OPTIONAL,
    	...,
    	typeOfUpdate [0] TypeOfUpdate OPTIONAL,
    	mtrf-SupportedAndAuthorized [1] NULL OPTIONAL,
    	mtrf-SupportedAndNotAuthorized [2] NULL OPTIONAL,
    	newMSC-Number [3] ISDN-AddressString OPTIONAL,
    	newVLR-Number [4] ISDN-AddressString OPTIONAL --unused:,
    	--unused:new-lmsi [5] LMSI OPTIONAL
    },
	data-v1 [UNIVERSAL 16] SEQUENCE {
    	identity Identity,
    	cancellationType CancellationType OPTIONAL,
    	extensionContainer ExtensionContainer OPTIONAL,
    	...,
    	typeOfUpdate [0] TypeOfUpdate OPTIONAL,
    	mtrf-SupportedAndAuthorized [1] NULL OPTIONAL,
    	mtrf-SupportedAndNotAuthorized [2] NULL OPTIONAL,
    	newMSC-Number [3] ISDN-AddressString OPTIONAL,
    	newVLR-Number [4] ISDN-AddressString OPTIONAL --unused:,
    	--unused:new-lmsi [5] LMSI OPTIONAL
    },
	imsi [UNIVERSAL 4] IMSI
}

TypeOfUpdate ::= ENUMERATED {
    sgsn-change (0),
    mme-change (1),
    ...}
-- TypeOfUpdate shall be absent if CancellationType is different from updateProcedure

CancellationType ::= ENUMERATED {
    updateProcedure (0),
    subscriptionWithdraw (1),
    ...,
    initialAttachProcedure (2)}
    -- The HLR shall not send values other than listed above

CancelLocationRes ::= SEQUENCE {
--unused:    extensionContainer ExtensionContainer OPTIONAL,
    ...}

--* PurgeMS-Arg ::= [3] SEQUENCE {
--     imsi IMSI,
--     vlr-Number [0] ISDN-AddressString OPTIONAL,
--     sgsn-Number [1] ISDN-AddressString OPTIONAL,
--     extensionContainer ExtensionContainer OPTIONAL,
--     ...}

PurgeMS-Arg ::= CHOICE {
	data-v2 [3] SEQUENCE {
    	imsi IMSI,
    	--unused:vlr-Number [0] ISDN-AddressString OPTIONAL,
    	--unused:sgsn-Number [1] ISDN-AddressString OPTIONAL,
    	--unused:extensionContainer ExtensionContainer OPTIONAL,
    	...},
    data-v1 [UNIVERSAL 16] SEQUENCE {
    	imsi IMSI,
    	--unused:vlr-Number [0] ISDN-AddressString OPTIONAL,
    	--unused:sgsn-Number [1] ISDN-AddressString OPTIONAL,
    	--unused:extensionContainer ExtensionContainer OPTIONAL,
    	...},
	imsi [UNIVERSAL 4] IMSI
}

--unused:PurgeMS-Res ::= SEQUENCE {
--unused:    freezeTMSI [0] NULL OPTIONAL,
--unused:    freezeP-TMSI [1] NULL OPTIONAL,
--unused:    extensionContainer ExtensionContainer OPTIONAL,
--unused:    ...,
--unused:    freezeM-TMSI [2] NULL OPTIONAL }

--* SendIdentificationArg ::= SEQUENCE {
--    tmsi TMSI,
--    numberOfRequestedVectors NumberOfRequestedVectors OPTIONAL,
--    -|- within a dialogue numberOfRequestedVectors shall be present in
--    -|- the first service request and shall not be present in subsequent service requests.
--    -|- If received in a subsequent service request it shall be discarded.
--    segmentationProhibited NULL OPTIONAL,
--    extensionContainer ExtensionContainer OPTIONAL,
--    ...,
--    msc-Number ISDN-AddressString OPTIONAL,
--    previous-LAI [0] LAIFixedLength OPTIONAL,
--    hopCounter [1] HopCounter OPTIONAL,
--    mtRoamingForwardingSupported [2] NULL OPTIONAL,
--    newVLR-Number [3] ISDN-AddressString OPTIONAL,
--    new-lmsi [4] LMSI OPTIONAL }

SendIdentificationArg ::= CHOICE {
 	data SEQUENCE {
    	tmsi TMSI,
    	numberOfRequestedVectors NumberOfRequestedVectors OPTIONAL,
    	-- within a dialogue numberOfRequestedVectors shall be present in
    	-- the first service request and shall not be present in subsequent service requests.
    	-- If received in a subsequent service request it shall be discarded.
    	segmentationProhibited NULL OPTIONAL,
    	extensionContainer ExtensionContainer OPTIONAL,
    	...,
    	msc-Number ISDN-AddressString OPTIONAL,
    	previous-LAI [0] LAIFixedLength OPTIONAL,
    	hopCounter [1] HopCounter OPTIONAL,
    	mtRoamingForwardingSupported [2] NULL OPTIONAL,
    	newVLR-Number [3] ISDN-AddressString OPTIONAL,
    	new-lmsi [4] LMSI OPTIONAL 
    },
	tmsi TMSI
}

HopCounter ::= INTEGER (0..3)

--* SendIdentificationRes ::= [3] SEQUENCE {
--     imsi IMSI OPTIONAL,
--     -|- IMSI shall be present in the first (or only) service response of a dialogue.
--     -|- If multiple service requests are present in a dialogue then IMSI
--     -|- shall not be present in any service response other than the first one.
--     authenticationSetList AuthenticationSetList OPTIONAL,
--     currentSecurityContext [2]CurrentSecurityContext OPTIONAL,
--     extensionContainer [3] ExtensionContainer OPTIONAL,
--     ...}
--     -|- authentication management types

SendIdentificationRes ::= CHOICE {
	data-v2 [3] SEQUENCE {
    	imsi IMSI OPTIONAL,
    	-- IMSI shall be present in the first (or only) service response of a dialogue.
    	-- If multiple service requests are present in a dialogue then IMSI
    	-- shall not be present in any service response other than the first one.
    	--unused:authenticationSetList AuthenticationSetList OPTIONAL,
    	--unused:currentSecurityContext [2]CurrentSecurityContext OPTIONAL,
    	--unused:extensionContainer [3] ExtensionContainer OPTIONAL,
    	...},
	data-v1 SEQUENCE {
  		imsi IMSI OPTIONAL,
  		--unused:tripletList TripletList OPTIONAL,
  		...}
}

AuthenticationSetList ::= CHOICE {
    tripletList [0] TripletList,
    quintupletList [1] QuintupletList }

TripletList ::= SEQUENCE SIZE (1..5) OF
    AuthenticationTriplet

QuintupletList ::= SEQUENCE SIZE (1..5) OF
    AuthenticationQuintuplet

AuthenticationTriplet ::= SEQUENCE {
    rand RAND,
    sres SRES,
    kc Kc,
    ...}

AuthenticationQuintuplet ::= SEQUENCE {
    rand RAND,
    xres XRES,
    ck CK,
    ik IK,
    autn AUTN,
    ...}

CurrentSecurityContext ::= CHOICE {
    gsm-SecurityContextData [0] GSM-SecurityContextData,
    umts-SecurityContextData [1] UMTS-SecurityContextData }
 
GSM-SecurityContextData ::= SEQUENCE {
    kc Kc,
    cksn Cksn,
    ... }

UMTS-SecurityContextData ::= SEQUENCE {
    ck CK,
    ik IK,
    ksi KSI,
    ... }

RAND ::= OCTET STRING (SIZE (16))

SRES ::= OCTET STRING (SIZE (4))

Kc ::= OCTET STRING (SIZE (8))

XRES ::= OCTET STRING (SIZE (4..16))

CK ::= OCTET STRING (SIZE (16))

IK ::= OCTET STRING (SIZE (16))

AUTN ::= OCTET STRING (SIZE (16))

AUTS ::= OCTET STRING (SIZE (14))

Cksn ::= OCTET STRING (SIZE (1))
    -- The internal structure is defined in 3GPP TS 24.008

KSI ::= OCTET STRING (SIZE (1))
    -- The internal structure is defined in 3GPP TS 24.008

AuthenticationFailureReportArg ::= SEQUENCE {
    imsi IMSI,
    failureCause FailureCause,  --unused
    --unused:extensionContainer ExtensionContainer OPTIONAL,
    ... --unused:,
    --unused:re-attempt BOOLEAN OPTIONAL,
    --unused:accessType AccessType OPTIONAL,
    --unused:rand RAND OPTIONAL,
    --unused:vlr-Number [0] ISDN-AddressString OPTIONAL,
    --unused:sgsn-Number [1] ISDN-AddressString OPTIONAL-- }

--unused:AccessType ::= ENUMERATED {
--unused:    call (0),
--unused:    emergencyCall (1),
--unused:    locationUpdating (2),
--unused:    supplementaryService (3),
--unused:    shortMessage (4),
--unused:    gprsAttach (5),
--unused:    routingAreaUpdating (6),
--unused:    serviceRequest (7),
--unused:    pdpContextActivation (8),
--unused:    pdpContextDeactivation (9),
--unused:    ...,
--unused:    gprsDetach (10)}
    -- exception handling:
    -- received values greater than 10 shall be ignored.

--unused:AuthenticationFailureReportRes ::= SEQUENCE {
--unused:    extensionContainer ExtensionContainer OPTIONAL,
--unused:    ...}

FailureCause ::= ENUMERATED {
    wrongUserResponse (0),
    wrongNetworkSignature (1)}

   -- gprs location registration types
UpdateGprsLocationArg ::= SEQUENCE {
    imsi IMSI,
    sgsn-Number ISDN-AddressString,                   --unused
    sgsn-Address GSN-Address,                         --unused
    extensionContainer ExtensionContainer OPTIONAL,
    ... ,
    sgsn-Capability [0] SGSN-Capability OPTIONAL,     --unused
    informPreviousNetworkEntity [1] NULL OPTIONAL,    --unused
    ps-LCS-NotSupportedByUE [2] NULL OPTIONAL,        --unused
    v-gmlc-Address [3] GSN-Address OPTIONAL,          --unused
    add-info [4] ADD-Info OPTIONAL,                   ...
    --unused:eps-info [5] EPS-Info OPTIONAL,
    --unused:servingNodeTypeIndicator [6] NULL OPTIONAL,
    --unused:skipSubscriberDataUpdate [7] NULL OPTIONAL,
    --unused:usedRAT-Type [8] Used-RAT-Type OPTIONAL,
    --unused:gprsSubscriptionDataNotNeeded [9] NULL OPTIONAL,
    --unused:nodeTypeIndicator [10] NULL OPTIONAL,
    --unused:areaRestricted [11] NULL OPTIONAL,
    --unused:ue-reachableIndicator [12] NULL OPTIONAL,
    --unused:epsSubscriptionDataNotNeeded [13] NULL OPTIONAL,
    --unused:ue-srvcc-Capability [14] UE-SRVCC-Capability OPTIONAL-- }

Used-RAT-Type::= ENUMERATED {
    utran (0),
    geran (1),
    gan (2),
    i-hspa-evolution (3),
    e-utran (4),
    ...}

--unused:EPS-Info ::= CHOICE {
--unused:    pdn-gw-update [0] PDN-GW-Update,
--unused:    isr-Information [1] ISR-Information }

--unused:PDN-GW-Update ::= SEQUENCE {
--unused:    apn [0] APN OPTIONAL,
--unused:    pdn-gw-Identity [1] PDN-GW-Identity OPTIONAL,
--unused:    contextId [2] ContextId OPTIONAL,
--unused:    extensionContainer [3] ExtensionContainer OPTIONAL,
--unused:    ... }
    -- The pdn-gw-update IE shall include the pdn-gw-Identity, and the apn or/and the contextID.
    -- The HSS shall ignore the eps-info IE if it includes a pdn-gw-update IE which does not
    -- include pdn-gw-Identity.
    -- The pdn-gw-Identity is defined as OPTIONAL for backward compatility reason with
    -- outdated earlier versions of this specification.

--unused:ISR-Information::= BIT STRING {
--unused:    updateMME (0),
--unused:    cancelSGSN (1),
--unused:    initialAttachIndicator (2)} (SIZE (3..8))
    -- exception handling: reception of unknown bit assignments in the
    -- ISR-Information data type shall be discarded by the receiver

SGSN-Capability ::= SEQUENCE {
    solsaSupportIndicator NULL OPTIONAL,
    extensionContainer [1] ExtensionContainer OPTIONAL,
    ... ,
    superChargerSupportedInServingNetworkEntity [2] SuperChargerInfo OPTIONAL ,
    gprsEnhancementsSupportIndicator [3] NULL OPTIONAL,
    supportedCamelPhases [4] SupportedCamelPhases OPTIONAL,
    supportedLCS-CapabilitySets [5] SupportedLCS-CapabilitySets OPTIONAL,
    offeredCamel4CSIs [6] OfferedCamel4CSIs OPTIONAL,
    smsCallBarringSupportIndicator [7] NULL OPTIONAL,
    supportedRAT-TypesIndicator [8] SupportedRAT-Types OPTIONAL,
    supportedFeatures [9] SupportedFeatures OPTIONAL,
    t-adsDataRetrieval [10] NULL OPTIONAL,
    homogeneousSupportOfIMSVoiceOverPSSessions [11] BOOLEAN OPTIONAL
    -- "true" indicates homogeneous support, "false" indicates homogeneous non-support
    -- in the complete SGSN area
    }

SupportedFeatures::= BIT STRING {
    odb-all-apn (0),
    odb-HPLMN-APN (1),
    odb-VPLMN-APN (2),
    odb-all-og (3),
    odb-all-international-og (4),
    odb-all-int-og-not-to-HPLMN-country (5),
    odb-all-interzonal-og (6),
    odb-all-interzonal-og-not-to-HPLMN-country (7),
    odb-all-interzonal-og-and-internat-og-not-to-HPLMN-country (8),
    regSub (9),
    trace (10),
    lcs-all-PrivExcep (11),
    lcs-universal (12),
    lcs-CallSessionRelated (13),
    lcs-CallSessionUnrelated (14),
    lcs-PLMN-operator (15),
    lcs-ServiceType (16),
    lcs-all-MOLR-SS (17),
    lcs-basicSelfLocation (18),
    lcs-autonomousSelfLocation (19),
    lcs-transferToThirdParty (20),
    sm-mo-pp (21),
    barring-OutgoingCalls (22),
    baoc (23),
    boic (24),
    boicExHC (25)} (SIZE (26..40))

--unused:UE-SRVCC-Capability::= ENUMERATED {
--unused:    ue-srvcc-not-supported (0),
--unused:    ue-srvcc-supported (1),
--unused:    ...}

UpdateGprsLocationRes ::= SEQUENCE {
    hlr-Number ISDN-AddressString,
    extensionContainer ExtensionContainer OPTIONAL,
    ... --unused:,
    --unused:add-Capability NULL OPTIONAL,
    --unused:sgsn-mmeSeparationSupported [0] NULL OPTIONAL-- }

-- handover types

--unused:ForwardAccessSignalling-Arg ::= [3] SEQUENCE {
--unused:    an-APDU AccessNetworkSignalInfo,
--unused:    integrityProtectionInfo [0] IntegrityProtectionInformation OPTIONAL,
--unused:    encryptionInfo [1] EncryptionInformation OPTIONAL,
--unused:    keyStatus [2] KeyStatus OPTIONAL,
--unused:    allowedGSM-Algorithms [4] AllowedGSM-Algorithms OPTIONAL,
--unused:    allowedUMTS-Algorithms [5] AllowedUMTS-Algorithms OPTIONAL,
--unused:    radioResourceInformation [6] RadioResourceInformation OPTIONAL,
--unused:    extensionContainer [3] ExtensionContainer OPTIONAL,
--unused:    ...,
--unused:    radioResourceList [7] RadioResourceList OPTIONAL,
--unused:    bssmap-ServiceHandover [9] BSSMAP-ServiceHandover OPTIONAL,
--unused:    ranap-ServiceHandover [8] RANAP-ServiceHandover OPTIONAL,
--unused:    bssmap-ServiceHandoverList [10] BSSMAP-ServiceHandoverList OPTIONAL,
--unused:    currentlyUsedCodec [11] Codec OPTIONAL,
--unused:    iuSupportedCodecsList [12] SupportedCodecsList OPTIONAL,
--unused:    rab-ConfigurationIndicator [13] NULL OPTIONAL,
--unused:    iuSelectedCodec [14] Codec OPTIONAL,
--unused:    alternativeChannelType [15] RadioResourceInformation OPTIONAL,
--unused:    tracePropagationList [17] TracePropagationList OPTIONAL,
--unused:    aoipSupportedCodecsListAnchor [18] AoIPCodecsList OPTIONAL,
--unused:    aoipSelectedCodecTarget [19] AoIPCodec OPTIONAL }

AllowedGSM-Algorithms ::= OCTET STRING (SIZE (1))
    -- internal structure is coded as Algorithm identifier octet from
    -- Permitted Algorithms defined in 3GPP TS 48.008
    -- A node shall mark all GSM algorithms that are allowed in MSC-B

AllowedUMTS-Algorithms ::= SEQUENCE {
    integrityProtectionAlgorithms [0] PermittedIntegrityProtectionAlgorithms OPTIONAL,
    encryptionAlgorithms [1] PermittedEncryptionAlgorithms OPTIONAL,
    extensionContainer [2] ExtensionContainer OPTIONAL,
    ...}

PermittedIntegrityProtectionAlgorithms ::=
    OCTET STRING (SIZE (1..maxPermittedIntegrityProtectionAlgorithmsLength))
    -- Octets contain a complete PermittedIntegrityProtectionAlgorithms data type
    -- as defined in 3GPP TS 25.413, encoded according to the encoding scheme
    -- mandated by 3GPP TS 25.413.
    -- Padding bits are included, if needed, in the least significant bits of the
    -- last octet of the octet string.

maxPermittedIntegrityProtectionAlgorithmsLength INTEGER ::= 9

PermittedEncryptionAlgorithms ::=
    OCTET STRING (SIZE (1..maxPermittedEncryptionAlgorithmsLength))
    -- Octets contain a complete PermittedEncryptionAlgorithms data type
    -- as defined in 3GPP TS 25.413, encoded according to the encoding scheme
    -- mandated by 3GPP TS 25.413
    -- Padding bits are included, if needed, in the least significant bits of the
    -- last octet of the octet string.

maxPermittedEncryptionAlgorithmsLength INTEGER ::= 9

--unused:KeyStatus ::= ENUMERATED {
--unused:    old (0),
--unused:    new (1),
--unused:    ...}
    -- exception handling:
    -- received values in range 2-31 shall be treated as "old"
    -- received values greater than 31 shall be treated as "new"

PrepareHO-Arg ::= [3] SEQUENCE {
	targetCellId [0] GlobalCellId OPTIONAL,                              --unused
	ho-NumberNotRequired NULL OPTIONAL,                                  --unused
	targetRNCId [1] RNCId OPTIONAL,                                      --unused
	an-APDU [2] AccessNetworkSignalInfo OPTIONAL,                        --unused
	multipleBearerRequested [3] NULL OPTIONAL,                           --unused
	imsi [4] IMSI OPTIONAL,
	integrityProtectionInfo [5] IntegrityProtectionInformation OPTIONAL, --unused
	encryptionInfo [6] EncryptionInformation OPTIONAL,                   --unused
	radioResourceInformation [7] RadioResourceInformation OPTIONAL,      --unused
	allowedGSM-Algorithms [9] AllowedGSM-Algorithms OPTIONAL,            --unused
	allowedUMTS-Algorithms [10] AllowedUMTS-Algorithms OPTIONAL,         --unused
	radioResourceList [11] RadioResourceList OPTIONAL,                   --unused
	extensionContainer [8] ExtensionContainer OPTIONAL,                  --unused
	... ,
	rab-Id [12] RAB-Id OPTIONAL,                                         --unused
	bssmap-ServiceHandover [13] BSSMAP-ServiceHandover OPTIONAL,         --unused
	ranap-ServiceHandover [14] RANAP-ServiceHandover OPTIONAL,           --unused
	bssmap-ServiceHandoverList [15] BSSMAP-ServiceHandoverList OPTIONAL, --unused
	asciCallReference [20] ASCI-CallReference OPTIONAL,                  --unused
	geran-classmark [16] GERAN-Classmark OPTIONAL,                       --unused
	iuCurrentlyUsedCodec [17] Codec OPTIONAL,                            --unused
	iuSupportedCodecsList [18] SupportedCodecsList OPTIONAL,             --unused
	rab-ConfigurationIndicator [19] NULL OPTIONAL,                       --unused
	uesbi-Iu [21] UESBI-Iu OPTIONAL,                                     --unused
	imeisv [22] IMEI OPTIONAL,                                           ...
	--unused:alternativeChannelType [23] RadioResourceInformation OPTIONAL,
	--unused:tracePropagationList [25] TracePropagationList OPTIONAL,
	--unused:aoipSupportedCodecsListAnchor [26] AoIPCodecsList OPTIONAL,
	--unused:regionalSubscriptionData [27] ZoneCodeList OPTIONAL,
	--unused:globalCallReference [28] LCLS-GlobalCallReference OPTIONAL,
	--unused:lcls-Negotiation [29] LCLS-Negotiation OPTIONAL-- }

--unused:LCLS-GlobalCallReference ::= OCTET STRING (SIZE (13..15))
	-- Octets are coded as specified in 3GPP TS 29.205 [146]

--unused:LCLS-Negotiation::= BIT STRING {
--unused:	permission-indicator (0),
--unused:	forward-data-sending-indicator (1),
--unused:	backward-sending-indicator (2),
--unused:	forward-data-reception-indicator (3),
--unused:	backward-data-reception-indicator (4)} (SIZE (5..8))
	-- exception handling: bits 5 to 7 shall be ignored if received and not understood

BSSMAP-ServiceHandoverList ::= SEQUENCE SIZE (1.. maxNumOfServiceHandovers) OF
	BSSMAP-ServiceHandoverInfo

BSSMAP-ServiceHandoverInfo ::= SEQUENCE {
	bssmap-ServiceHandover BSSMAP-ServiceHandover,
	rab-Id RAB-Id,
	-- RAB Identity is needed to relate the service handovers with the radio access bearers.
	...}

maxNumOfServiceHandovers INTEGER ::= 7
BSSMAP-ServiceHandover ::= OCTET STRING (SIZE (1))
	-- Octets are coded according the Service Handover information element in
	-- 3GPP TS 48.008.

RANAP-ServiceHandover ::= OCTET STRING (SIZE (1))
	-- Octet contains a complete Service-Handover data type
	-- as defined in 3GPP TS 25.413, encoded according to the encoding scheme
	-- mandated by 3GPP TS 25.413
	-- Padding bits are included in the least significant bits.
RadioResourceList ::= SEQUENCE SIZE (1.. maxNumOfRadioResources) OF
	RadioResource

RadioResource ::= SEQUENCE {
	radioResourceInformation RadioResourceInformation,
	rab-Id RAB-Id,
	-- RAB Identity is needed to relate the radio resources with the radio access bearers.
	...}

	maxNumOfRadioResources INTEGER ::= 7

--unused:PrepareHO-Res ::= [3] SEQUENCE {
--unused:	handoverNumber [0] ISDN-AddressString OPTIONAL,
--unused:	relocationNumberList [1] RelocationNumberList OPTIONAL,
--unused:	an-APDU [2] AccessNetworkSignalInfo OPTIONAL,
--unused:	multicallBearerInfo [3] MulticallBearerInfo OPTIONAL,
--unused:	multipleBearerNotSupported NULL OPTIONAL,
--unused:	selectedUMTS-Algorithms [5] SelectedUMTS-Algorithms OPTIONAL,
--unused:	chosenRadioResourceInformation [6] ChosenRadioResourceInformation OPTIONAL,
--unused:	extensionContainer [4] ExtensionContainer OPTIONAL,
--unused:	...,
--unused:	iuSelectedCodec [7] Codec OPTIONAL,
--unused:	iuAvailableCodecsList [8] CodecList OPTIONAL,
--unused:	aoipSelectedCodecTarget [9] AoIPCodec OPTIONAL,
--unused:	aoipAvailableCodecsListMap [10] AoIPCodecsList OPTIONAL }
--unused:	SelectedUMTS-Algorithms ::= SEQUENCE {
--unused:	integrityProtectionAlgorithm [0] ChosenIntegrityProtectionAlgorithm OPTIONAL,
--unused:	encryptionAlgorithm [1] ChosenEncryptionAlgorithm OPTIONAL,
--unused:	extensionContainer [2] ExtensionContainer OPTIONAL,
--unused:	...}

ChosenIntegrityProtectionAlgorithm ::= OCTET STRING (SIZE (1))
	-- Octet contains a complete IntegrityProtectionAlgorithm data type
	-- as defined in 3GPP TS 25.413, encoded according to the encoding scheme
	-- mandated by 3GPP TS 25.413
	-- Padding bits are included in the least significant bits.

ChosenEncryptionAlgorithm ::= OCTET STRING (SIZE (1))
	-- Octet contains a complete EncryptionAlgorithm data type
	-- as defined in 3GPP TS 25.413, encoded according to the encoding scheme
	-- mandated by 3GPP TS 25.413
	-- Padding bits are included in the least significant bits.

ChosenRadioResourceInformation ::= SEQUENCE {
	chosenChannelInfo [0] ChosenChannelInfo OPTIONAL,
	chosenSpeechVersion [1] ChosenSpeechVersion OPTIONAL,
	...}

ChosenChannelInfo ::= OCTET STRING (SIZE (1))
	-- Octets are coded according the Chosen Channel information element in 3GPP TS 48.008

ChosenSpeechVersion ::= OCTET STRING (SIZE (1))
	-- Octets are coded according the Speech Version (chosen) information element in 3GPP TS
	-- 48.008

--unused:PrepareSubsequentHO-Arg ::= [3] SEQUENCE {
--unused:	targetCellId [0] GlobalCellId OPTIONAL,
--unused:	targetMSC-Number [1] ISDN-AddressString,
--unused:	targetRNCId [2] RNCId OPTIONAL,
--unused:	an-APDU [3] AccessNetworkSignalInfo OPTIONAL,
--unused:	selectedRab-Id [4] RAB-Id OPTIONAL,
--unused:	extensionContainer [5] ExtensionContainer OPTIONAL,
--unused:	...,
--unused:	geran-classmark [6] GERAN-Classmark OPTIONAL,
--unused:	rab-ConfigurationIndicator [7] NULL OPTIONAL }
--unused:PrepareSubsequentHO-Res ::= [3] SEQUENCE {
--unused:	an-APDU AccessNetworkSignalInfo,
--unused:	extensionContainer [0] ExtensionContainer OPTIONAL,
--unused:	...}

--* ProcessAccessSignalling-Arg ::= [3] SEQUENCE {
-- 	an-APDU AccessNetworkSignalInfo,
-- 	selectedUMTS-Algorithms [1] SelectedUMTS-Algorithms OPTIONAL,
-- 	selectedGSM-Algorithm [2] SelectedGSM-Algorithm OPTIONAL,
-- 	chosenRadioResourceInformation [3] ChosenRadioResourceInformation OPTIONAL,
-- 	selectedRab-Id [4] RAB-Id OPTIONAL,
-- 	extensionContainer [0] ExtensionContainer OPTIONAL,
-- 	...,
-- 	iUSelectedCodec [5] Codec OPTIONAL,
-- 	iuAvailableCodecsList [6] CodecList OPTIONAL,
-- 	aoipSelectedCodecTarget [7] AoIPCodec OPTIONAL,
-- 	aoipAvailableCodecsListMap [8] AoIPCodecsList OPTIONAL }

--unused:ProcessAccessSignalling-Arg ::= CHOICE {
--unused:	data-v2 [3] SEQUENCE {
--unused:		an-APDU AccessNetworkSignalInfo,
--unused:		selectedUMTS-Algorithms [1] SelectedUMTS-Algorithms OPTIONAL,
--unused:		selectedGSM-Algorithm [2] SelectedGSM-Algorithm OPTIONAL,
--unused:		chosenRadioResourceInformation [3] ChosenRadioResourceInformation OPTIONAL,
--unused:		selectedRab-Id [4] RAB-Id OPTIONAL,
--unused:		extensionContainer [0] ExtensionContainer OPTIONAL,
--unused:		...,
--unused:		iUSelectedCodec [5] Codec OPTIONAL,
--unused:		iuAvailableCodecsList [6] CodecList OPTIONAL,
--unused:		aoipSelectedCodecTarget [7] AoIPCodec OPTIONAL,
--unused:		aoipAvailableCodecsListMap [8] AoIPCodecsList OPTIONAL 
--unused:	},
--unused:	an-APDU AccessNetworkSignalInfo
--unused:}

AoIPCodecsList ::= SEQUENCE {
	codec1 [1] AoIPCodec,
	codec2 [2] AoIPCodec OPTIONAL,
	codec3 [3] AoIPCodec OPTIONAL,
	codec4 [4] AoIPCodec OPTIONAL,
	codec5 [5] AoIPCodec OPTIONAL,
	codec6 [6] AoIPCodec OPTIONAL,
	codec7 [7] AoIPCodec OPTIONAL,
	codec8 [8] AoIPCodec OPTIONAL,
	extensionContainer [9] ExtensionContainer OPTIONAL,
	...}
	-- Codecs are sent in priority order where codec1 has highest priority

AoIPCodec ::= OCTET STRING (SIZE (1..3))
	-- The internal structure is defined as follows:
	-- octet 1 Coded as Speech Codec Elements in 3GPP TS 48.008
	-- with the exception that FI, PI, PT and TF bits shall
	-- be set to 0
	-- octets 2,3 Optional; in case of AMR codec types it defines
	-- the supported codec configurations as defined in
	-- 3GPP TS 48.008

SupportedCodecsList ::= SEQUENCE {
	utranCodecList [0] CodecList OPTIONAL,
	geranCodecList [1] CodecList OPTIONAL,
	extensionContainer [2] ExtensionContainer OPTIONAL,
	...}

CodecList ::= SEQUENCE {
	codec1 [1] Codec,
	codec2 [2] Codec OPTIONAL,
	codec3 [3] Codec OPTIONAL,
	codec4 [4] Codec OPTIONAL,
	codec5 [5] Codec OPTIONAL,
	codec6 [6] Codec OPTIONAL,
	codec7 [7] Codec OPTIONAL,
	codec8 [8] Codec OPTIONAL,
	extensionContainer [9] ExtensionContainer OPTIONAL,
	...}
	-- Codecs are sent in priority order where codec1 has highest priority

Codec ::= OCTET STRING (SIZE (1..4))
	-- The internal structure is defined as follows:
	-- octet 1 Coded as Codec Identification code in 3GPP TS 26.103
	-- octets 2,3,4 Parameters for the Codec as defined in 3GPP TS
	-- 26.103, if available, length depending on the codec

GERAN-Classmark ::= OCTET STRING (SIZE (2..87))
	-- Octets are coded according the GERAN Classmark information element in 3GPP TS 48.008

SelectedGSM-Algorithm ::= OCTET STRING (SIZE (1))
	-- internal structure is coded as Algorithm identifier octet from Chosen Encryption
	-- Algorithm defined in 3GPP TS 48.008
	-- A node shall mark only the selected GSM algorithm

--* SendEndSignal-Arg ::= [3] SEQUENCE {
-- 	an-APDU AccessNetworkSignalInfo,
-- 	extensionContainer [0] ExtensionContainer OPTIONAL,
-- 	...}

--unused:SendEndSignal-Arg ::= CHOICE {
--unused:	data [3] SEQUENCE {
--unused:		an-APDU AccessNetworkSignalInfo,
--unused:		extensionContainer [0] ExtensionContainer OPTIONAL,
--unused:		...},
--unused:	an-APDU AccessNetworkSignalInfo
--unused:}

--unused:SendEndSignal-Res ::= SEQUENCE {
--unused:	extensionContainer [0] ExtensionContainer OPTIONAL,
--unused:	...}

RNCId ::= OCTET STRING (SIZE (7))
	-- The internal structure is defined as follows:
	-- octet 1 bits 4321 Mobile Country Code 1st digit
	-- bits 8765 Mobile Country Code 2nd digit
	-- octet 2 bits 4321 Mobile Country Code 3rd digit
	-- bits 8765 Mobile Network Code 3rd digit
	-- or filler (1111) for 2 digit MNCs
	-- octet 3 bits 4321 Mobile Network Code 1st digit
	-- bits 8765 Mobile Network Code 2nd digit
	-- octets 4 and 5 Location Area Code according to 3GPP TS 24.008
	-- octets 6 and 7 RNC Id value according to 3GPP TS 25.413

RelocationNumberList ::= SEQUENCE SIZE (1..maxNumOfRelocationNumber) OF
	RelocationNumber

MulticallBearerInfo ::= INTEGER (1..maxNumOfRelocationNumber)

RelocationNumber ::= SEQUENCE {
	handoverNumber ISDN-AddressString,
	rab-Id RAB-Id,
	-- RAB Identity is needed to relate the calls with the radio access bearers.
	...}

RAB-Id ::= INTEGER (1..maxNrOfRABs)

maxNrOfRABs INTEGER ::= 255

maxNumOfRelocationNumber INTEGER ::= 7

RadioResourceInformation ::= OCTET STRING (SIZE (3..13))
	-- Octets are coded according the Channel Type information element in 3GPP TS 48.008
	
IntegrityProtectionInformation ::= OCTET STRING (SIZE (18..maxNumOfIntegrityInfo))
	-- Octets contain a complete IntegrityProtectionInformation data type
	-- as defined in 3GPP TS 25.413, encoded according to the encoding scheme
	-- mandated by 3GPP TS 25.413
	-- Padding bits are included, if needed, in the least significant bits of the
	-- last octet of the octet string.

maxNumOfIntegrityInfo INTEGER ::= 100

EncryptionInformation ::= OCTET STRING (SIZE (18..maxNumOfEncryptionInfo))
	-- Octets contain a complete EncryptionInformation data type
	-- as defined in 3GPP TS 25.413, encoded according to the encoding scheme
	-- mandated by 3GPP TS 25.413
	-- Padding bits are included, if needed, in the least significant bits of the
	-- last octet of the octet string.

maxNumOfEncryptionInfo INTEGER ::= 100

-- authentication management types
-- ?* SendAuthenticationInfoArg ::= SEQUENCE {
-- 	 imsi [0] IMSI,
-- 	 numberOfRequestedVectors NumberOfRequestedVectors,
-- 	 segmentationProhibited NULL OPTIONAL,
-- 	 immediateResponsePreferred [1] NULL OPTIONAL,
-- 	 re-synchronisationInfo Re-synchronisationInfo OPTIONAL,
-- 	 extensionContainer [2] ExtensionContainer OPTIONAL,
-- 	 ...,
-- 	 requestingNodeType [3] RequestingNodeType OPTIONAL,
-- 	 requestingPLMN-Id [4] PLMN-Id OPTIONAL,
-- 	 numberOfRequestedAdditional-Vectors [5] NumberOfRequestedVectors OPTIONAL,
-- 	 additionalVectorsAreForEPS [6] NULL OPTIONAL }
SendAuthenticationInfoArg ::= CHOICE {
	authInfo [UNIVERSAL 16] SEQUENCE {
		imsi [0] IMSI,
		numberOfRequestedVectors NumberOfRequestedVectors,
		segmentationProhibited NULL OPTIONAL,
		immediateResponsePreferred [1] NULL OPTIONAL,
		re-synchronisationInfo Re-synchronisationInfo OPTIONAL,
		extensionContainer [2] ExtensionContainer OPTIONAL,
		...,
		requestingNodeType [3] RequestingNodeType OPTIONAL,
		requestingPLMN-Id [4] PLMN-Id OPTIONAL,
		numberOfRequestedAdditional-Vectors [5] NumberOfRequestedVectors OPTIONAL,
		additionalVectorsAreForEPS [6] NULL OPTIONAL },
	imsi [UNIVERSAL 4] IMSI
}

SendAuthenticationInfoArg-empty ::= [UNIVERSAL 16] SEQUENCE { }

NumberOfRequestedVectors ::= INTEGER (1..5)

Re-synchronisationInfo ::= SEQUENCE {
	rand RAND,
	auts AUTS,
	...}

-- ?* SendAuthenticationInfoRes ::= [3] SEQUENCE {
--       authenticationSetList AuthenticationSetList OPTIONAL,
--       extensionContainer ExtensionContainer OPTIONAL,
--       ...,
--       eps-AuthenticationSetList [2] EPS-AuthenticationSetList OPTIONAL }

SendAuthenticationInfoRes ::= CHOICE {
	authInfoOld [UNIVERSAL 16] SEQUENCE  ( SIZE( 1 .. 5 ) ) OF
		AuthenticationTripletV1 --AuthInfoOldItem--,
	authInfoNew [3] SEQUENCE {
		authenticationSetList AuthenticationSetList OPTIONAL,
		extensionContainer ExtensionContainer OPTIONAL,
		...,
		eps-AuthenticationSetList [2] EPS-AuthenticationSetList OPTIONAL }
}

AuthenticationTripletV1 ::= SEQUENCE { --unused:AuthInfoOldItem ::= SEQUENCE {
    rand RAND,                         --unused:            rand       RAND, 
    sres SRES,                         --unused:            sres       SRES, 
    kc Kc                              --unused:            kc         Kc, 
    }                                  --unused:            ... }

EPS-AuthenticationSetList ::= SEQUENCE SIZE (1..5) OF
	EPC-AV

EPC-AV ::= SEQUENCE {
	rand RAND,
	xres XRES,
	autn AUTN,
	kasme KASME,
	extensionContainer ExtensionContainer OPTIONAL,
	...}

KASME ::= OCTET STRING (SIZE (32))

RequestingNodeType ::= ENUMERATED {
	vlr (0),
	sgsn (1),
	...,
	s-cscf (2),
	bsf (3),
	gan-aaa-server (4),
	wlan-aaa-server (5),
	mme (16),
	mme-sgsn (17)
	}
	-- the values 2, 3, 4 and 5 shall not be used on the MAP-D or Gr interfaces
	-- exception handling:
	-- received values in the range (6-15) shall be treated as "vlr"
	-- received values greater than 17 shall be treated as "sgsn"

-- equipment management types

CheckIMEI-Arg ::= SEQUENCE {
	imei IMEI,
	--unused:CHOICE { requestedEquipmentInfo-v1 [PRIVATE 1] RequestedEquipmentInfo, requestedEquipmentInfo-v3 [UNIVERSAL 3] RequestedEquipmentInfo },
	--unused:extensionContainer ExtensionContainer OPTIONAL,
	...}

UniversalCheckIMEI-Arg ::= SEQUENCE {
	imei IMEI,
	...}

--unused:CheckIMEI-Res ::= SEQUENCE {
--unused:	equipmentStatus EquipmentStatus OPTIONAL,
--unused:	bmuef UESBI-Iu OPTIONAL,
--unused:	extensionContainer [0] ExtensionContainer OPTIONAL,
--unused:	...}

--unused:RequestedEquipmentInfo::= BIT STRING {
--unused:	equipmentStatus (0),
--unused:	bmuef (1)} (SIZE (2..8))
	-- exception handling: reception of unknown bit assignments in the
	-- RequestedEquipmentInfo data type shall be discarded by the receiver

UESBI-Iu ::= SEQUENCE {
	uesbi-IuA [0] UESBI-IuA OPTIONAL,
	uesbi-IuB [1] UESBI-IuB OPTIONAL,
	...}

UESBI-IuA ::= BIT STRING (SIZE(1..128))
	-- See 3GPP TS 25.413

UESBI-IuB ::= BIT STRING (SIZE(1..128))
	-- See 3GPP TS 25.413

--unused:EquipmentStatus ::= ENUMERATED {
--unused:	whiteListed (0),
--unused:	blackListed (1),
--unused:	greyListed (2)}

-- subscriber management types

InsertSubscriberDataArg ::= SEQUENCE {
    imsi [0] IMSI OPTIONAL,
-- COMPONENTS OF SubscriberData,
	msisdn [1] ISDN-AddressString OPTIONAL,
	category [2] Category OPTIONAL,
	subscriberStatus [3] SubscriberStatus OPTIONAL,
	bearerServiceList [4] BearerServiceList OPTIONAL,
	-- The exception handling for reception of unsupported / not allocated
	-- bearerServiceCodes is defined in section 8.8.1
	teleserviceList [6] TeleserviceList OPTIONAL,
	-- The exception handling for reception of unsupported / not allocated
	-- teleserviceCodes is defined in section 8.8.1
	provisionedSS [7] Ext-SS-InfoList OPTIONAL,
	odb-Data [8] ODB-Data OPTIONAL,
	roamingRestrictionDueToUnsupportedFeature [9] NULL OPTIONAL,
	regionalSubscriptionData [10] ZoneCodeList OPTIONAL,
	vbsSubscriptionData [11] VBSDataList OPTIONAL,
	vgcsSubscriptionData [12] VGCSDataList OPTIONAL,
	vlrCamelSubscriptionInfo [13] VlrCamelSubscriptionInfo OPTIONAL,
-- End OF COMPONENTS OF SubscriberData
    --unused:extensionContainer [14] ExtensionContainer OPTIONAL,
    ... --unused:,
    --unused:naea-PreferredCI [15] NAEA-PreferredCI OPTIONAL,
    --unused:- - naea-PreferredCI is included at the discretion of the HLR operator.
    --unused:gprsSubscriptionData [16] GPRSSubscriptionData OPTIONAL,
    --unused:roamingRestrictedInSgsnDueToUnsupportedFeature [23] NULL OPTIONAL,
    --unused:networkAccessMode [24] NetworkAccessMode OPTIONAL,
    --unused:lsaInformation [25] LSAInformation OPTIONAL,
    --unused:lmu-Indicator [21] NULL OPTIONAL,
    --unused:lcsInformation [22] LCSInformation OPTIONAL,
    --unused:istAlertTimer [26] IST-AlertTimerValue OPTIONAL,
    --unused:superChargerSupportedInHLR [27] AgeIndicator OPTIONAL,
    --unused:mc-SS-Info [28] MC-SS-Info OPTIONAL,
    --unused:cs-AllocationRetentionPriority [29] CS-AllocationRetentionPriority OPTIONAL,
    --unused:sgsn-CAMEL-SubscriptionInfo [17] SGSN-CAMEL-SubscriptionInfo OPTIONAL,
    --unused:chargingCharacteristics [18] ChargingCharacteristics OPTIONAL,
    --unused:accessRestrictionData [19] AccessRestrictionData OPTIONAL,
    --unused:ics-Indicator [20] BOOLEAN OPTIONAL,
    --unused:eps-SubscriptionData [31] EPS-SubscriptionData OPTIONAL,
    --unused:csg-SubscriptionDataList [32] CSG-SubscriptionDataList OPTIONAL,
    --unused:ue-ReachabilityRequestIndicator [33] NULL OPTIONAL,
    --unused:sgsn-Number [34] ISDN-AddressString OPTIONAL,
    --unused:mme-Name [35] DiameterIdentity OPTIONAL,
    --unused:subscribedPeriodicRAUTAUtimer [36] SubscribedPeriodicRAUTAUtimer OPTIONAL,
    --unused:vplmnLIPAAllowed [37] NULL OPTIONAL,
    --unused:mdtUserConsent [38] BOOLEAN OPTIONAL,
    --unused:subscribedPeriodicLAUtimer [39] SubscribedPeriodicLAUtimer OPTIONAL,
    --unused:additionalMSISDN [41] ISDN-AddressString OPTIONAL-- }
    -- If the Network Access Mode parameter is sent, it shall be present only in
    -- the first sequence if seqmentation is used

--unused:SubscribedPeriodicRAUTAUtimer ::= INTEGER (0..4294967295)
	-- This parameter carries the subscribed periodic TAU/RAU timer value in seconds.

--unused:SubscribedPeriodicLAUtimer ::= INTEGER (0..4294967295)
	-- This parameter carries the subscribed periodic LAU timer value in seconds.

--unused:CSG-SubscriptionDataList ::= SEQUENCE SIZE (1..50) OF
--unused:    CSG-SubscriptionData

--unused:CSG-SubscriptionData ::= SEQUENCE {
--unused:    csg-Id CSG-Id,
--unused:    expirationDate Time OPTIONAL,
--unused:    extensionContainer ExtensionContainer OPTIONAL,
--unused:    ...,
--unused:    lipa-AllowedAPNList [0] LIPA-AllowedAPNList OPTIONAL
--unused:    }

CSG-Id ::= BIT STRING (SIZE (27))
    -- coded according to 3GPP TS 23.003 [17].

--unused:LIPA-AllowedAPNList ::= SEQUENCE SIZE (1..maxNumOfLIPAAllowedAPN) OF
--unused:    APN
--unused:
--unused:maxNumOfLIPAAllowedAPN INTEGER ::= 50

--unused:EPS-SubscriptionData ::= SEQUENCE {
--unused:    apn-oi-Replacement [0] APN-OI-Replacement OPTIONAL,
--unused:    - - this apn-oi-Replacement refers to the UE level apn-oi-Replacement.
--unused:    rfsp-id [2] RFSP-ID OPTIONAL,
--unused:    ambr [3] AMBR OPTIONAL,
--unused:    apn-ConfigurationProfile [4] APN-ConfigurationProfile OPTIONAL,
--unused:    stn-sr [6] ISDN-AddressString OPTIONAL,
--unused:    extensionContainer [5] ExtensionContainer OPTIONAL,
--unused:    ...,
--unused:    mps-CSPriority [7] NULL OPTIONAL,
--unused:    mps-EPSPriority [8] NULL OPTIONAL }
   -- mps-CSPriority by its presence indicates that the UE is subscribed to the eMLPP in
   -- the CS domain, referring to the 3GPP TS 29.272 [144] for details.
   -- mps-EPSPriority by its presence indicates that the UE is subscribed to the MPS in
   -- the EPS domain, referring to the 3GPP TS 29.272 [144] for details.

--unused:APN-OI-Replacement ::= OCTET STRING (SIZE (9..100))
    -- Octets are coded as APN Operator Identifier according to TS 3GPP TS 23.003 [17]

--unused:RFSP-ID ::= INTEGER (1..256)

--unused:APN-ConfigurationProfile ::= SEQUENCE {
--unused:    defaultContext ContextId,
--unused:    completeDataListIncluded NULL OPTIONAL,
--unused:    - - If segmentation is used, completeDataListIncluded may only be present in the
--unused:    - - first segment of APN-ConfigurationProfile.
--unused:    epsDataList [1] EPS-DataList,
--unused:    extensionContainer [2] ExtensionContainer OPTIONAL,
--unused:    ...}

--unused:EPS-DataList ::= SEQUENCE SIZE (1..maxNumOfAPN-Configurations) OF
--unused:	APN-Configuration

--unused:maxNumOfAPN-Configurations INTEGER ::= 50

--unused:APN-Configuration ::= SEQUENCE {
--unused:	contextId [0] ContextId,
--unused:	pdn-Type [1] PDN-Type,
--unused:	servedPartyIP-IPv4-Address [2] PDP-Address OPTIONAL,
--unused:	apn [3] APN,
--unused:	eps-qos-Subscribed [4] EPS-QoS-Subscribed,
--unused:	pdn-gw-Identity [5] PDN-GW-Identity OPTIONAL,
--unused:	pdn-gw-AllocationType [6] PDN-GW-AllocationType OPTIONAL,
--unused:	vplmnAddressAllowed [7] NULL OPTIONAL,
--unused:	chargingCharacteristics [8] ChargingCharacteristics OPTIONAL,
--unused:	ambr [9] AMBR OPTIONAL,
--unused:	specificAPNInfoList [10] SpecificAPNInfoList OPTIONAL,
--unused:	extensionContainer [11] ExtensionContainer OPTIONAL,
--unused:	servedPartyIP-IPv6-Address [12] PDP-Address OPTIONAL,
--unused:	...,
--unused:	apn-oi-Replacement [13] APN-OI-Replacement OPTIONAL,
--unused:	- - this apn-oi-Replacement refers to the APN level apn-oi-Replacement.
--unused:	sipto-Permission [14] SIPTO-Permission OPTIONAL,
--unused:	lipa-Permission [15] LIPA-Permission OPTIONAL
--unused:	}

--unused:PDN-Type ::= OCTET STRING (SIZE (1))
	-- Octet is coded according to TS 3GPP TS 29.274 [140]

--unused:EPS-QoS-Subscribed ::= SEQUENCE {
--unused:	qos-Class-Identifier [0] QoS-Class-Identifier,
--unused:	allocation-Retention-Priority [1] Allocation-Retention-Priority,
--unused:	extensionContainer [2] ExtensionContainer OPTIONAL,
--unused:	... }

--unused:AMBR ::= SEQUENCE {
--unused:	max-RequestedBandwidth-UL [0] Bandwidth,
--unused:	max-RequestedBandwidth-DL [1] Bandwidth,
--unused:	extensionContainer [2] ExtensionContainer OPTIONAL,
--unused:	... }

--unused:SpecificAPNInfoList ::= SEQUENCE SIZE (1..maxNumOfSpecificAPNInfos) OF
--unused:	SpecificAPNInfo

--unused:maxNumOfSpecificAPNInfos INTEGER ::= 50

--unused:SpecificAPNInfo ::= SEQUENCE {
--unused:	apn [0] APN,
--unused:	pdn-gw-Identity [1] PDN-GW-Identity,
--unused:	extensionContainer [2] ExtensionContainer OPTIONAL,
--unused:	... }

--unused:Bandwidth ::= INTEGER
	-- bits per second

--unused:QoS-Class-Identifier ::= INTEGER (1..9)
	-- values are defined in 3GPP TS 29.212

--unused:Allocation-Retention-Priority ::= SEQUENCE {
--unused:	priority-level [0] INTEGER,
--unused:	pre-emption-capability [1] BOOLEAN OPTIONAL,
--unused:	pre-emption-vulnerability [2] BOOLEAN OPTIONAL,
--unused:	extensionContainer [3] ExtensionContainer OPTIONAL,
--unused:	... }

--unused:PDN-GW-Identity ::= SEQUENCE {
--unused:	pdn-gw-ipv4-Address [0] PDP-Address OPTIONAL,
--unused:	pdn-gw-ipv6-Address [1] PDP-Address OPTIONAL,
--unused:	pdn-gw-name [2] FQDN OPTIONAL,
--unused:	extensionContainer [3] ExtensionContainer OPTIONAL,
--unused:	... }

--unused:FQDN ::= OCTET STRING (SIZE (9..255))

--unused:PDN-GW-AllocationType ::= ENUMERATED {
--unused:	static (0),
--unused:	dynamic (1)}

--unused:AccessRestrictionData ::= BIT STRING {
--unused:	utranNotAllowed (0),
--unused:	geranNotAllowed (1),
--unused:	ganNotAllowed (2),
--unused:	i-hspa-evolutionNotAllowed (3),
--unused:	e-utranNotAllowed (4),
--unused:	ho-toNon3GPP-AccessNotAllowed (5) } (SIZE (2..8))
	-- exception handling:
	-- access restriction data related to an access type not supported by a node
	-- shall be ignored
	-- bits 6 to 7 shall be ignored if received and not understood

--unused:CS-AllocationRetentionPriority ::= OCTET STRING (SIZE (1))
	-- This data type encodes each priority level defined in TS 23.107 as the binary value
	-- of the priority level.

IST-AlertTimerValue ::= INTEGER (15..255)

--unused:LCSInformation ::= SEQUENCE {
--unused:	gmlc-List [0] GMLC-List OPTIONAL,
--unused:	lcs-PrivacyExceptionList [1] LCS-PrivacyExceptionList OPTIONAL,
--unused:	molr-List [2] MOLR-List OPTIONAL,
--unused:	...,
--unused:	add-lcs-PrivacyExceptionList [3] LCS-PrivacyExceptionList OPTIONAL }
	-- add-lcs-PrivacyExceptionList may be sent only if lcs-PrivacyExceptionList is
	-- present and contains four instances of LCS-PrivacyClass. If the mentioned condition
	-- is not satisfied the receiving node shall discard add-lcs-PrivacyExceptionList.
	-- If an LCS-PrivacyClass is received both in lcs-PrivacyExceptionList and in
	-- add-lcs-PrivacyExceptionList with the same SS-Code, then the error unexpected
	-- data value shall be returned.

--unused:GMLC-List ::= SEQUENCE SIZE (1..maxNumOfGMLC) OF
--unused:	ISDN-AddressString
	-- if segmentation is used, the complete GMLC-List shall be sent in one segment

--unused:maxNumOfGMLC INTEGER ::= 5

--unused:NetworkAccessMode ::= ENUMERATED {
--unused:	packetAndCircuit (0),
--unused:	onlyCircuit (1),
--unused:	onlyPacket (2),
--unused:	...}
	-- if unknown values are received in NetworkAccessMode
	-- they shall be discarded.

--unused:GPRSDataList ::= SEQUENCE SIZE (1..maxNumOfPDP-Contexts) OF
--unused:	PDP-Context

maxNumOfPDP-Contexts INTEGER ::= 50

--unused:PDP-Context ::= SEQUENCE {
--unused:	pdp-ContextId ContextId,
--unused:	pdp-Type [16] PDP-Type,
--unused:	pdp-Address [17] PDP-Address OPTIONAL,
--unused:	qos-Subscribed [18] QoS-Subscribed,
--unused:	vplmnAddressAllowed [19] NULL OPTIONAL,
--unused:	apn [20] APN,
--unused:	extensionContainer [21] ExtensionContainer OPTIONAL,
--unused:	... ,
--unused:	ext-QoS-Subscribed [0] Ext-QoS-Subscribed OPTIONAL,
--unused:	pdp-ChargingCharacteristics [1] ChargingCharacteristics OPTIONAL,
--unused:	ext2-QoS-Subscribed [2] Ext2-QoS-Subscribed OPTIONAL,
--unused:	- - ext2-QoS-Subscribed may be present only if ext-QoS-Subscribed is present.
--unused:	ext3-QoS-Subscribed [3] Ext3-QoS-Subscribed OPTIONAL,
--unused:	- - ext3-QoS-Subscribed may be present only if ext2-QoS-Subscribed is present.
--unused:	ext4-QoS-Subscribed [4] Ext4-QoS-Subscribed OPTIONAL,
--unused:	- - ext4-QoS-Subscribed may be present only if ext3-QoS-Subscribed is present.
--unused:	apn-oi-Replacement [5] APN-OI-Replacement OPTIONAL,
--unused:	- - this apn-oi-Replacement refers to the APN level apn-oi-Replacement and has
--unused:	- - higher priority than UE level apn-oi-Replacement.
--unused:	ext-pdp-Type [6] Ext-PDP-Type OPTIONAL,
--unused:	- - contains the value IPv4v6 defined in 3GPP TS 29.060 [105], if the PDP can be
--unused:	- - accessed by dual-stack UEs
--unused:	ext-pdp-Address [7] PDP-Address OPTIONAL,
--unused:	- - contains an additional IP address in case of dual-stack static IP address assignment
--unused:	- - for the UE.
--unused:	- - it may contain an IPv4 or an IPv6 address/prefix, and it may be present
--unused:	- - only if pdp-Address is present; if both are present, each parameter shall
--unused:	- - contain a different type of address (IPv4 or IPv6).
--unused:	ambr [10] AMBR OPTIONAL,
--unused:	- - this ambr contains the AMBR associated to the APN included in the
--unused:	- - PDP-Context (APN-AMBR).
--unused:	sipto-Permission [8] SIPTO-Permission OPTIONAL,
--unused:	lipa-Permission [9] LIPA-Permission OPTIONAL
--unused:	}

--unused:SIPTO-Permission ::= ENUMERATED {
--unused:	siptoAllowed (0),
--unused:	siptoNotAllowed (1)
--unused:	}

--unused:LIPA-Permission ::= ENUMERATED {
--unused:	lipaProhibited (0),
--unused:	lipaOnly (1),
--unused:	lipaConditional (2)
--unused:	}

ContextId ::= INTEGER (1..maxNumOfPDP-Contexts)

--unused:GPRSSubscriptionData ::= SEQUENCE {
--unused:	completeDataListIncluded NULL OPTIONAL,
--unused:	- - If segmentation is used, completeDataListIncluded may only be present in the
--unused:	- - first segment of GPRSSubscriptionData.
--unused:	gprsDataList [1] GPRSDataList,
--unused:	extensionContainer [2] ExtensionContainer OPTIONAL,
--unused:	...,
--unused:	apn-oi-Replacement [3] APN-OI-Replacement OPTIONAL
--unused:	- - this apn-oi-Replacement refers to the UE level apn-oi-Replacement.
--unused:	}

--unused:SGSN-CAMEL-SubscriptionInfo ::= SEQUENCE {
--unused:	gprs-CSI [0] GPRS-CSI OPTIONAL,
--unused:	mo-sms-CSI [1] SMS-CSI OPTIONAL,
--unused:	extensionContainer [2] ExtensionContainer OPTIONAL,
--unused:	...,
--unused:	mt-sms-CSI [3] SMS-CSI OPTIONAL,
--unused:	mt-smsCAMELTDP-CriteriaList [4] MT-smsCAMELTDP-CriteriaList OPTIONAL,
--unused:	mg-csi [5] MG-CSI OPTIONAL
--unused:	}

GPRS-CSI ::= SEQUENCE {
	gprs-CamelTDPDataList [0] GPRS-CamelTDPDataList OPTIONAL,
	camelCapabilityHandling [1] CamelCapabilityHandling OPTIONAL,
	extensionContainer [2] ExtensionContainer OPTIONAL,
	notificationToCSE [3] NULL OPTIONAL,
	csi-Active [4] NULL OPTIONAL,
	...}
	-- notificationToCSE and csi-Active shall not be present when GPRS-CSI is sent to SGSN.
	-- They may only be included in ATSI/ATM ack/NSDC message.
	-- GPRS-CamelTDPData and camelCapabilityHandling shall be present in
	-- the GPRS-CSI sequence.
	-- If GPRS-CSI is segmented, gprs-CamelTDPDataList and camelCapabilityHandling shall be
	-- present in the first segment

GPRS-CamelTDPDataList ::= SEQUENCE SIZE (1..maxNumOfCamelTDPData) OF
	GPRS-CamelTDPData
	-- GPRS-CamelTDPDataList shall not contain more than one instance of
	-- GPRS-CamelTDPData containing the same value for gprs-TriggerDetectionPoint.

GPRS-CamelTDPData ::= SEQUENCE {
	gprs-TriggerDetectionPoint [0] GPRS-TriggerDetectionPoint,
	serviceKey [1] ServiceKey,
	gsmSCF-Address [2] ISDN-AddressString,
	defaultSessionHandling [3] DefaultGPRS-Handling,
	extensionContainer [4] ExtensionContainer OPTIONAL,
	...
	}

DefaultGPRS-Handling ::= ENUMERATED {
	continueTransaction (0) ,
	releaseTransaction (1) ,
	...}
	-- exception handling:
	-- reception of values in range 2-31 shall be treated as "continueTransaction"
	-- reception of values greater than 31 shall be treated as "releaseTransaction"

GPRS-TriggerDetectionPoint ::= ENUMERATED {
	attach (1),
	attachChangeOfPosition (2),
	pdp-ContextEstablishment (11),
	pdp-ContextEstablishmentAcknowledgement (12),
	pdp-ContextChangeOfPosition (14),
	... }
	-- exception handling:
	-- For GPRS-CamelTDPData sequences containing this parameter with any
	-- other value than the ones listed the receiver shall ignore the whole
	-- GPRS-CamelTDPDatasequence.

APN ::= OCTET STRING (SIZE (2..63))
	-- Octets are coded according to TS 3GPP TS 23.003 [17]

PDP-Type ::= OCTET STRING (SIZE (2))
	-- Octets are coded according to TS 3GPP TS 29.060 [105]
	-- Only the values PPP, IPv4 and IPv6 are allowed for this parameter.

Ext-PDP-Type ::= OCTET STRING (SIZE (2))
	-- Octets are coded, similarly to PDP-Type, according to TS 3GPP TS 29.060 [105].
	-- Only the value IPv4v6 is allowed for this parameter.

PDP-Address ::= OCTET STRING (SIZE (1..16))
	-- Octets are coded according to TS 3GPP TS 29.060 [105]
	-- The possible size values are:
	-- 1-7 octets X.25 address type
	-- 4 octets IPv4 address type
	-- 16 octets Ipv6 address type

--unused:QoS-Subscribed ::= OCTET STRING (SIZE (3))
	-- Octets are coded according to TS 3GPP TS 24.008 [35] Quality of Service Octets
	-- 3-5.

Ext-QoS-Subscribed ::= OCTET STRING (SIZE (1..9))
	-- OCTET 1:
	-- Allocation/Retention Priority (This octet encodes each priority level defined in
	-- 23.107 as the binary value of the priority level, declaration in 29.060)
	-- Octets 2-9 are coded according to 3GPP TS 24.008 [35] Quality of Service Octets
	-- 6-13.

Ext2-QoS-Subscribed ::= OCTET STRING (SIZE (1..3))
	-- Octets 1-3 are coded according to 3GPP TS 24.008 [35] Quality of Service Octets 14-16.
	-- If Quality of Service information is structured with 14 octet length, then
	-- Octet 1 is coded according to 3GPP TS 24.008 [35] Quality of Service Octet 14.

Ext3-QoS-Subscribed ::= OCTET STRING (SIZE (1..2))
	-- Octets 1-2 are coded according to 3GPP TS 24.008 [35] Quality of Service Octets 17-18.

Ext4-QoS-Subscribed ::= OCTET STRING (SIZE (1))
	-- Octet 1:
	-- Evolved Allocation/Retention Priority. This octet encodes the Priority Level (PL),
	-- the Preemption Capability (PCI) and Preemption Vulnerability (PVI) values, as
	-- described in 3GPP TS 29.060 [105].

ChargingCharacteristics ::= OCTET STRING (SIZE (2))
	-- Octets are coded according to 3GPP TS 32.215.

--unused:LSAOnlyAccessIndicator ::= ENUMERATED {
--unused:	accessOutsideLSAsAllowed (0),
--unused:	accessOutsideLSAsRestricted (1)}

--unused:LSADataList ::= SEQUENCE SIZE (1..maxNumOfLSAs) OF
--unused:	LSAData
--unused:
--unused:maxNumOfLSAs INTEGER ::= 20
--unused:
--unused:LSAData ::= SEQUENCE {
--unused:	lsaIdentity [0] LSAIdentity,
--unused:	lsaAttributes [1] LSAAttributes,
--unused:	lsaActiveModeIndicator [2] NULL OPTIONAL,
--unused:	extensionContainer [3] ExtensionContainer OPTIONAL,
--unused:	...}

--unused:LSAInformation ::= SEQUENCE {
--unused:	completeDataListIncluded NULL OPTIONAL,
--unused:	- - If segmentation is used, completeDataListIncluded may only be present in the
--unused:	- - first segment.
--unused:	lsaOnlyAccessIndicator [1] LSAOnlyAccessIndicator OPTIONAL,
--unused:	lsaDataList [2] LSADataList OPTIONAL,
--unused:	extensionContainer [3] ExtensionContainer OPTIONAL,
--unused:	...}

	LSAIdentity ::= OCTET STRING (SIZE (3))
	-- Octets are coded according to TS 3GPP TS 23.003 [17]

	LSAAttributes ::= OCTET STRING (SIZE (1))
	-- Octets are coded according to TS 3GPP TS 48.008 [49]

--unused:SubscriberData ::= SEQUENCE {
--unused:	msisdn [1] ISDN-AddressString OPTIONAL, ...
--unused:	category [2] Category OPTIONAL,
--unused:	subscriberStatus [3] SubscriberStatus OPTIONAL,
--unused:	- -unused:bearerServiceList [4] BearerServiceList OPTIONAL,
--unused:	- - The exception handling for reception of unsupported / not allocated
--unused:	- - bearerServiceCodes is defined in section 8.8.1
--unused:	teleserviceList [6] TeleserviceList OPTIONAL,
--unused:	- - The exception handling for reception of unsupported / not allocated
--unused:	- - teleserviceCodes is defined in section 8.8.1
--unused:	provisionedSS [7] Ext-SS-InfoList OPTIONAL,
--unused:	odb-Data [8] ODB-Data OPTIONAL,
--unused:	roamingRestrictionDueToUnsupportedFeature [9] NULL OPTIONAL,
--unused:	regionalSubscriptionData [10] ZoneCodeList OPTIONAL,
--unused:	vbsSubscriptionData [11] VBSDataList OPTIONAL,
--unused:	vgcsSubscriptionData [12] VGCSDataList OPTIONAL,
--unused:	vlrCamelSubscriptionInfo [13] VlrCamelSubscriptionInfo OPTIONAL
--unused:	}

Category ::= OCTET STRING (SIZE (1))
    -- The internal structure is defined in ITU-T Rec Q.763.

SubscriberStatus ::= ENUMERATED {
    serviceGranted (0),
    operatorDeterminedBarring (1)}

BearerServiceList ::= SEQUENCE SIZE (1..maxNumOfBearerServices) OF
    Ext-BearerServiceCode

maxNumOfBearerServices INTEGER ::= 50

TeleserviceList ::= SEQUENCE SIZE (1..maxNumOfTeleservices) OF
    Ext-TeleserviceCode

maxNumOfTeleservices INTEGER ::= 20

ODB-Data ::= SEQUENCE {
    odb-GeneralData ODB-GeneralData,
    odb-HPLMN-Data ODB-HPLMN-Data OPTIONAL,
    --unused:extensionContainer ExtensionContainer OPTIONAL,
    ...}

ODB-GeneralData ::= BIT STRING {
    allOG-CallsBarred (0),
    internationalOGCallsBarred (1),
    internationalOGCallsNotToHPLMN-CountryBarred (2),
    interzonalOGCallsBarred (6),
    interzonalOGCallsNotToHPLMN-CountryBarred (7),
    interzonalOGCallsAndInternationalOGCallsNotToHPLMN-CountryBarred (8),
    premiumRateInformationOGCallsBarred (3),
    premiumRateEntertainementOGCallsBarred (4),
    ss-AccessBarred (5),
    allECT-Barred (9),
    chargeableECT-Barred (10),
    internationalECT-Barred (11),
    interzonalECT-Barred (12),
    doublyChargeableECT-Barred (13),
    multipleECT-Barred (14),
    allPacketOrientedServicesBarred (15),
    roamerAccessToHPLMN-AP-Barred (16),
    roamerAccessToVPLMN-AP-Barred (17),
    roamingOutsidePLMNOG-CallsBarred (18),
    allIC-CallsBarred (19),
    roamingOutsidePLMNIC-CallsBarred (20),
    roamingOutsidePLMNICountryIC-CallsBarred (21),
    roamingOutsidePLMN-Barred (22),
    roamingOutsidePLMN-CountryBarred (23),
    registrationAllCF-Barred (24),
    registrationCFNotToHPLMN-Barred (25),
    registrationInterzonalCF-Barred (26),
    registrationInterzonalCFNotToHPLMN-Barred (27),
    registrationInternationalCF-Barred (28)} (SIZE (15..32))
    -- exception handling: reception of unknown bit assignments in the
    -- ODB-GeneralData type shall be treated like unsupported ODB-GeneralData
    -- When the ODB-GeneralData type is removed from the HLR for a given subscriber,
    -- in NoteSubscriberDataModified operation sent toward the gsmSCF
    -- all bits shall be set to “O“.

ODB-HPLMN-Data ::= BIT STRING {
	plmn-SpecificBarringType1 (0),
	plmn-SpecificBarringType2 (1),
	plmn-SpecificBarringType3 (2),
	plmn-SpecificBarringType4 (3)} (SIZE (4..32))
	-- exception handling: reception of unknown bit assignments in the
	-- ODB-HPLMN-Data type shall be treated like unsupported ODB-HPLMN-Data
	-- When the ODB-HPLMN-Data type is removed from the HLR for a given subscriber,
	-- in NoteSubscriberDataModified operation sent toward the gsmSCF
	-- all bits shall be set to “O“.

Ext-SS-InfoList ::= SEQUENCE SIZE (1..maxNumOfSS) OF
	Ext-SS-Info

Ext-SS-Info ::= CHOICE {
 forwardingInfo  [0] Ext-ForwInfo,
 callBarringInfo  [1] Ext-CallBarInfo,
 cug-Info   [2] CUG-Info,
 ss-Data   [3] Ext-SS-Data,
 emlpp-Info  [4] EMLPP-Info}

Ext-ForwInfo ::= SEQUENCE {
	ss-Code SS-Code,
	forwardingFeatureList Ext-ForwFeatureList,
	--unused:extensionContainer [0] ExtensionContainer OPTIONAL,
	...}

Ext-ForwFeatureList ::= SEQUENCE SIZE (1..maxNumOfExt-BasicServiceGroups) OF
	Ext-ForwFeature

Ext-ForwFeature ::= SEQUENCE {
	basicService Ext-BasicServiceCode OPTIONAL,
	ss-Status [4] Ext-SS-Status,
	forwardedToNumber [5] ISDN-AddressString OPTIONAL,
	-- When this data type is sent from an HLR which supports CAMEL Phase 2
	-- to a VLR that supports CAMEL Phase 2 the VLR shall not check the
	-- format of the number
	--unused:forwardedToSubaddress [8] ISDN-SubaddressString OPTIONAL,
	forwardingOptions [6] Ext-ForwOptions OPTIONAL,
	--unused:noReplyConditionTime [7] Ext-NoRepCondTime OPTIONAL,
	--unused:extensionContainer [9] ExtensionContainer OPTIONAL,
	...--unused:,
	--unused:longForwardedToNumber [10] FTN-AddressString OPTIONAL-- }

Ext-ForwOptions ::= OCTET STRING (SIZE (1..5))

	-- OCTET 1:     
	
	--   bit 8: notification to forwarding party
	--     0 no notification
	--     1 notification
	
	--   bit 7: redirecting presentation
	--     0 no presentation
	--     1 presentation
	
	--   bit 6: notification to calling party
	--     0 no notification
	--     1 notification
	
	--   bit 5: 0 (unused)
	
	--   bits 43: forwarding reason	
	--     00 ms not reachable
	--     01 ms busy
	--     10 no reply
	--     11 unconditional
	
	--   bits 21: 00 (unused)
	
	-- OCTETS 2-5: reserved for future use. They shall be discarded if
	-- received and not understood.

Ext-NoRepCondTime ::= INTEGER (1..100)
	-- Only values 5-30 are used.
	-- Values in the ranges 1-4 and 31-100 are reserved for future use
	-- If received:
	-- values 1-4 shall be mapped on to value 5
	-- values 31-100 shall be mapped on to value 30

Ext-CallBarInfo ::= SEQUENCE {
	ss-Code SS-Code,
	callBarringFeatureList Ext-CallBarFeatureList,
	extensionContainer ExtensionContainer OPTIONAL,
	...}

Ext-CallBarFeatureList ::= SEQUENCE SIZE (1..maxNumOfExt-BasicServiceGroups) OF
	Ext-CallBarringFeature

Ext-CallBarringFeature ::= SEQUENCE {
	basicService Ext-BasicServiceCode OPTIONAL,
	ss-Status [4] Ext-SS-Status,
	extensionContainer ExtensionContainer OPTIONAL,
	...}

CUG-Info ::= SEQUENCE {
	cug-SubscriptionList CUG-SubscriptionList,
	cug-FeatureList CUG-FeatureList OPTIONAL,
	extensionContainer [0] ExtensionContainer OPTIONAL,
	...}

CUG-SubscriptionList ::= SEQUENCE SIZE (0..maxNumOfCUG) OF
	CUG-Subscription

CUG-Subscription ::= SEQUENCE {
	cug-Index CUG-Index,
	cug-Interlock CUG-Interlock,
	intraCUG-Options IntraCUG-Options,
	basicServiceGroupList Ext-BasicServiceGroupList OPTIONAL,
	extensionContainer [0] ExtensionContainer OPTIONAL,
	...}

CUG-Index ::= INTEGER (0..32767)
	-- The internal structure is defined in ETS 300 138.

CUG-Interlock ::= OCTET STRING (SIZE (4))

IntraCUG-Options ::= ENUMERATED {
	noCUG-Restrictions (0),
	cugIC-CallBarred (1),
	cugOG-CallBarred (2)}

maxNumOfCUG INTEGER ::= 10

CUG-FeatureList ::= SEQUENCE SIZE (1..maxNumOfExt-BasicServiceGroups) OF
	CUG-Feature

Ext-BasicServiceGroupList ::= SEQUENCE SIZE (1..maxNumOfExt-BasicServiceGroups) OF
	Ext-BasicServiceCode

maxNumOfExt-BasicServiceGroups INTEGER ::= 32

CUG-Feature ::= SEQUENCE {
	basicService Ext-BasicServiceCode OPTIONAL,
	preferentialCUG-Indicator CUG-Index OPTIONAL,
	interCUG-Restrictions InterCUG-Restrictions,
	extensionContainer ExtensionContainer OPTIONAL,
	...}

InterCUG-Restrictions ::= OCTET STRING (SIZE (1))
	-- bits 876543: 000000 (unused)
	-- Exception handling:
	-- bits 876543 shall be ignored if received and not understood
	-- bits 21
	-- 00 CUG only facilities
	-- 01 CUG with outgoing access
	-- 10 CUG with incoming access
	-- 11 CUG with both outgoing and incoming access

Ext-SS-Data ::= SEQUENCE {
	ss-Code SS-Code,
	ss-Status [4] Ext-SS-Status,
	ss-SubscriptionOption SS-SubscriptionOption OPTIONAL,
	basicServiceGroupList Ext-BasicServiceGroupList OPTIONAL,
	extensionContainer [5] ExtensionContainer OPTIONAL,
	...}

--unused:LCS-PrivacyExceptionList ::= SEQUENCE SIZE (1..maxNumOfPrivacyClass) OF
--unused:	LCS-PrivacyClass

--unused:maxNumOfPrivacyClass INTEGER ::= 4

--unused:LCS-PrivacyClass ::= SEQUENCE {
--unused:	ss-Code SS-Code,
--unused:	ss-Status Ext-SS-Status,
--unused:	notificationToMSUser [0] NotificationToMSUser OPTIONAL,
--unused:	- - notificationToMSUser may be sent only for SS-codes callSessionRelated
--unused:	- - and callSessionUnrelated. If not received for SS-codes callSessionRelated
--unused:	- - and callSessionUnrelated,
--unused:	- - the default values according to 3GPP TS 23.271 shall be assumed.
--unused:	externalClientList [1] ExternalClientList OPTIONAL,
--unused:	- - externalClientList may be sent only for SS-code callSessionUnrelated to a
--unused:	- - visited node that does not support LCS Release 4 or later versions.
--unused:	- - externalClientList may be sent only for SS-codes callSessionUnrelated and
--unused:	- - callSessionRelated to a visited node that supports LCS Release 4 or later versions.
--unused:	plmnClientList [2] PLMNClientList OPTIONAL,
--unused:	- - plmnClientList may be sent only for SS-code plmnoperator.
--unused:	extensionContainer [3] ExtensionContainer OPTIONAL,
--unused:	...,
--unused:	ext-externalClientList [4] Ext-ExternalClientList OPTIONAL,
--unused:	- - Ext-externalClientList may be sent only if the visited node supports LCS Release 4 or
--unused:	- - later versions, the user did specify more than 5 clients, and White Book SCCP is used.
--unused:	serviceTypeList [5] ServiceTypeList OPTIONAL
--unused:	- - serviceTypeList may be sent only for SS-code serviceType and if the visited node
--unused:	- - supports LCS Release 5 or later versions.
--unused:	- -
--unused:	- - if segmentation is used, the complete LCS-PrivacyClass shall be sent in one segment
--unused:	}

--unused:ExternalClientList ::= SEQUENCE SIZE (0..maxNumOfExternalClient) OF
--unused:	ExternalClient
--unused:
--unused:maxNumOfExternalClient INTEGER ::= 5
--unused:
--unused:PLMNClientList ::= SEQUENCE SIZE (1..maxNumOfPLMNClient) OF
--unused:	LCSClientInternalID
--unused:
--unused:maxNumOfPLMNClient INTEGER ::= 5
--unused:
--unused:Ext-ExternalClientList ::= SEQUENCE SIZE (1..maxNumOfExt-ExternalClient) OF
--unused:	ExternalClient
--unused:
--unused:maxNumOfExt-ExternalClient INTEGER ::= 35

--unused:ExternalClient ::= SEQUENCE {
--unused:	clientIdentity LCSClientExternalID,
--unused:	gmlc-Restriction [0] GMLC-Restriction OPTIONAL,
--unused:	notificationToMSUser [1] NotificationToMSUser OPTIONAL,
--unused:	- - If notificationToMSUser is not received, the default value according to
--unused:	- - 3GPP TS 23.271 shall be assumed.
--unused:	extensionContainer [2] ExtensionContainer OPTIONAL,
--unused:	... }

GMLC-Restriction ::= ENUMERATED {
	gmlc-List (0),
	home-Country (1) ,
	... }
	-- exception handling:
	-- At reception of any other value than the ones listed the receiver shall ignore
	-- GMLC-Restriction.

NotificationToMSUser ::= ENUMERATED {
	notifyLocationAllowed (0),
	notifyAndVerify-LocationAllowedIfNoResponse (1),
	notifyAndVerify-LocationNotAllowedIfNoResponse (2),
	...,
	locationNotAllowed (3) }
	-- exception handling:
	-- At reception of any other value than the ones listed the receiver shall ignore
	-- NotificationToMSUser.

ServiceTypeList ::= SEQUENCE SIZE (1..maxNumOfServiceType) OF
	ServiceType

maxNumOfServiceType INTEGER ::= 32

ServiceType ::= SEQUENCE {
	serviceTypeIdentity LCSServiceTypeID,
	gmlc-Restriction [0] GMLC-Restriction OPTIONAL,
	notificationToMSUser [1] NotificationToMSUser OPTIONAL,
	-- If notificationToMSUser is not received, the default value according to
	-- 3GPP TS 23.271 shall be assumed.
	extensionContainer [2] ExtensionContainer OPTIONAL,
	... }

MOLR-List ::= SEQUENCE SIZE (1..maxNumOfMOLR-Class) OF
	MOLR-Class

maxNumOfMOLR-Class INTEGER ::= 3

MOLR-Class ::= SEQUENCE {
	ss-Code SS-Code,
	ss-Status Ext-SS-Status,
	extensionContainer [0] ExtensionContainer OPTIONAL,
	...}

ZoneCodeList ::= SEQUENCE SIZE (1..maxNumOfZoneCodes) OF
    ZoneCode

ZoneCode ::= OCTET STRING (SIZE (2))
    -- internal structure is defined in TS 3GPP TS 23.003 [17]

maxNumOfZoneCodes INTEGER ::= 10

InsertSubscriberDataRes ::= SEQUENCE {
    teleserviceList [1] TeleserviceList OPTIONAL,
    bearerServiceList [2] BearerServiceList OPTIONAL,
    ss-List [3] SS-List OPTIONAL,
    odb-GeneralData [4] ODB-GeneralData OPTIONAL,
    regionalSubscriptionResponse [5] RegionalSubscriptionResponse OPTIONAL,
    supportedCamelPhases [6] SupportedCamelPhases OPTIONAL,
    --unused:extensionContainer [7] ExtensionContainer OPTIONAL,
    ...--unused:,
    --unused:offeredCamel4CSIs [8] OfferedCamel4CSIs OPTIONAL,
    --unused:supportedFeatures [9] SupportedFeatures OPTIONAL-- }

RegionalSubscriptionResponse ::= ENUMERATED {
    networkNode-AreaRestricted (0),
    tooManyZoneCodes (1),
    zoneCodesConflict (2),
    regionalSubscNotSupported (3)}

DeleteSubscriberDataArg ::= SEQUENCE {
    imsi [0] IMSI,
    --unused:basicServiceList [1] BasicServiceList OPTIONAL,
    --unused:- - The exception handling for reception of unsupported/not allocated
    --unused:- - basicServiceCodes is defined in section 6.8.2
    --unused:ss-List [2] SS-List OPTIONAL,
    --unused:roamingRestrictionDueToUnsupportedFeature [4] NULL OPTIONAL,
    --unused:regionalSubscriptionIdentifier [5] ZoneCode OPTIONAL,
    --unused:vbsGroupIndication [7] NULL OPTIONAL,
    --unused:vgcsGroupIndication [8] NULL OPTIONAL,
    --unused:camelSubscriptionInfoWithdraw [9] NULL OPTIONAL,
    --unused:extensionContainer [6] ExtensionContainer OPTIONAL,
    ...--unused:,
    --unused:gprsSubscriptionDataWithdraw [10] GPRSSubscriptionDataWithdraw OPTIONAL,
    --unused:roamingRestrictedInSgsnDueToUnsuppportedFeature [11] NULL OPTIONAL,
    --unused:lsaInformationWithdraw [12] LSAInformationWithdraw OPTIONAL,
    --unused:gmlc-ListWithdraw [13] NULL OPTIONAL,
    --unused:istInformationWithdraw [14] NULL OPTIONAL,
    --unused:specificCSI-Withdraw [15] SpecificCSI-Withdraw OPTIONAL,
    --unused:chargingCharacteristicsWithdraw [16] NULL OPTIONAL,
    --unused:stn-srWithdraw [17] NULL OPTIONAL,
    --unused:epsSubscriptionDataWithdraw [18] EPS-SubscriptionDataWithdraw OPTIONAL,
    --unused:apn-oi-replacementWithdraw [19] NULL OPTIONAL,
    --unused:csg-SubscriptionDeleted [20] NULL OPTIONAL,
    --unused:subscribedPeriodicTAU-RAU-TimerWithdraw [22] NULL OPTIONAL,
    --unused:subscribedPeriodicLAU-TimerWithdraw [23] NULL OPTIONAL,
    --unused:subscribed-vsrvccWithdraw [21] NULL OPTIONAL,
    --unused:vplmn-Csg-SubscriptionDeleted [24] NULL OPTIONAL,
    --unused:additionalMSISDN-Withdraw [25] NULL OPTIONAL,
    --unused:cs-to-ps-SRVCC-Withdraw [26] NULL OPTIONAL,
    --unused:imsiGroupIdList-Withdraw [27] NULL OPTIONAL,
    --unused:userPlaneIntegrityProtectionWithdraw [28] NULL OPTIONAL,
    --unused:dl-Buffering-Suggested-Packet-Count-Withdraw [29] NULL OPTIONAL,
    --unused:ue-UsageTypeWithdraw [30] NULL OPTIONAL,
    --unused:reset-idsWithdraw [31] NULL OPTIONAL-- }

SpecificCSI-Withdraw ::= BIT STRING {
    o-csi (0),
    ss-csi (1),
    tif-csi (2),
    d-csi (3),
    vt-csi (4),
    mo-sms-csi (5),
    m-csi (6),
    gprs-csi (7),
    t-csi (8),
    mt-sms-csi (9),
    mg-csi (10),
    o-IM-CSI (11),
    d-IM-CSI (12),
    vt-IM-CSI (13) } (SIZE(8..32))
    -- exception handling:
    -- bits 11 to 31 shall be ignored if received by a non-IP Multimedia Core Network entity.
    -- bits 0-10 and 14-31 shall be ignored if received by an IP Multimedia Core Network entity.
    -- bits 11-13 are only applicable in an IP Multimedia Core Network.
    -- Bit 8 and bits 11-13 are only applicable for the NoteSubscriberDataModified operation.

--unused:GPRSSubscriptionDataWithdraw ::= CHOICE {
--unused:    allGPRSData NULL,
--unused:    contextIdList ContextIdList}

--unused:EPS-SubscriptionDataWithdraw ::= CHOICE {
--unused:    allEPS-Data NULL,
--unused:    contextIdList ContextIdList}

--unused:ContextIdList ::= SEQUENCE SIZE (1..maxNumOfPDP-Contexts) OF
--unused:    ContextId

--unused:LSAInformationWithdraw ::= CHOICE {
--unused:    allLSAData NULL,
--unused:    lsaIdentityList LSAIdentityList }

--unused:LSAIdentityList ::= SEQUENCE SIZE (1..maxNumOfLSAs) OF
--unused:    LSAIdentity

--unused:BasicServiceList ::= SEQUENCE SIZE (1..maxNumOfBasicServices) OF
--unused:    Ext-BasicServiceCode

--unused:maxNumOfBasicServices INTEGER ::= 70

--unused:DeleteSubscriberDataRes ::= SEQUENCE {
--unused:    regionalSubscriptionResponse [0] RegionalSubscriptionResponse OPTIONAL,
--unused:    extensionContainer ExtensionContainer OPTIONAL,
--unused:    ...}

VlrCamelSubscriptionInfo ::= SEQUENCE {
    o-CSI [0] O-CSI OPTIONAL,
    extensionContainer [1] ExtensionContainer OPTIONAL,
    ...,
    ss-CSI [2] SS-CSI OPTIONAL,
    o-BcsmCamelTDP-CriteriaList [4] O-BcsmCamelTDPCriteriaList OPTIONAL,
    tif-CSI [3] NULL OPTIONAL,
    m-CSI [5] M-CSI OPTIONAL,
    mo-sms-CSI [6] SMS-CSI OPTIONAL,
    vt-CSI [7] T-CSI OPTIONAL,
    t-BCSM-CAMEL-TDP-CriteriaList [8] T-BCSM-CAMEL-TDP-CriteriaList OPTIONAL,
    d-CSI [9] D-CSI OPTIONAL,
    mt-sms-CSI [10] SMS-CSI OPTIONAL,
    mt-smsCAMELTDP-CriteriaList [11] MT-smsCAMELTDP-CriteriaList OPTIONAL
    }

MT-smsCAMELTDP-CriteriaList ::= SEQUENCE SIZE (1.. maxNumOfCamelTDPData) OF
	MT-smsCAMELTDP-Criteria

MT-smsCAMELTDP-Criteria ::= SEQUENCE {
	sms-TriggerDetectionPoint SMS-TriggerDetectionPoint,
	tpdu-TypeCriterion [0] TPDU-TypeCriterion OPTIONAL,
	... }

TPDU-TypeCriterion ::= SEQUENCE SIZE (1..maxNumOfTPDUTypes) OF
	MT-SMS-TPDU-Type

maxNumOfTPDUTypes INTEGER ::= 5

MT-SMS-TPDU-Type ::= ENUMERATED {
	sms-DELIVER (0),
	sms-SUBMIT-REPORT (1),
	sms-STATUS-REPORT (2),
	...}
-- exception handling:
-- For TPDU-TypeCriterion sequences containing this parameter with any
-- other value than the ones listed above the receiver shall ignore
-- the whole TPDU-TypeCriterion sequence.
-- In CAMEL phase 4, sms-SUBMIT-REPORT shall not be used and a received TPDU-TypeCriterion
-- sequence containing sms-SUBMIT-REPORT shall be wholly ignored.

D-CSI ::= SEQUENCE {
	dp-AnalysedInfoCriteriaList [0] DP-AnalysedInfoCriteriaList OPTIONAL,
	camelCapabilityHandling [1] CamelCapabilityHandling OPTIONAL,
	extensionContainer [2] ExtensionContainer OPTIONAL,
	notificationToCSE [3] NULL OPTIONAL,
	csi-Active [4] NULL OPTIONAL,
	...}
	-- notificationToCSE and csi-Active shall not be present when D-CSI is sent to VLR/GMSC.
	-- They may only be included in ATSI/ATM ack/NSDC message.
	-- DP-AnalysedInfoCriteria and camelCapabilityHandling shall be present in
	-- the D-CSI sequence.
	-- If D-CSI is segmented, then the first segment shall contain dp-AnalysedInfoCriteriaList
	-- and camelCapabilityHandling. Subsequent segments shall not contain
	-- camelCapabilityHandling, but may contain dp-AnalysedInfoCriteriaList.

DP-AnalysedInfoCriteriaList ::= SEQUENCE SIZE (1..maxNumOfDP-AnalysedInfoCriteria) OF
	DP-AnalysedInfoCriterium

maxNumOfDP-AnalysedInfoCriteria INTEGER ::= 10

DP-AnalysedInfoCriterium ::= SEQUENCE {
	dialledNumber ISDN-AddressString,
	serviceKey ServiceKey,
	gsmSCF-Address ISDN-AddressString,
	defaultCallHandling DefaultCallHandling,
	extensionContainer ExtensionContainer OPTIONAL,
	...}

SS-CSI ::= SEQUENCE {
	ss-CamelData SS-CamelData,
	extensionContainer ExtensionContainer OPTIONAL,
	...,
	notificationToCSE [0] NULL OPTIONAL,
	csi-Active [1] NULL OPTIONAL
	-- notificationToCSE and csi-Active shall not be present when SS-CSI is sent to VLR.
	-- They may only be included in ATSI/ATM ack/NSDC message.
	}

SS-CamelData ::= SEQUENCE {
	ss-EventList SS-EventList,
	gsmSCF-Address ISDN-AddressString,
	extensionContainer [0] ExtensionContainer OPTIONAL,
	...}

SS-EventList ::= SEQUENCE SIZE (1..maxNumOfCamelSSEvents) OF SS-Code
	-- Actions for the following SS-Code values are defined in CAMEL Phase 3:
	-- ect SS-Code ::= '00110001'B
	-- multiPTY SS-Code ::= '01010001'B
	-- cd SS-Code ::= '00100100'B
	-- ccbs SS-Code ::= '01000100'B
	-- all other SS codes shall be ignored
	-- When SS-CSI is sent to the VLR, it shall not contain a marking for ccbs.
	-- If the VLR receives SS-CSI containing a marking for ccbs, the VLR shall discard the
	-- ccbs marking in SS-CSI.

maxNumOfCamelSSEvents INTEGER ::= 10

O-CSI ::= SEQUENCE {
	o-BcsmCamelTDPDataList O-BcsmCamelTDPDataList,
	extensionContainer ExtensionContainer OPTIONAL,
	...,
	camelCapabilityHandling [0] CamelCapabilityHandling OPTIONAL,
	notificationToCSE [1] NULL OPTIONAL,
	csiActive [2] NULL OPTIONAL}
-- notificationtoCSE and csiActive shall not be present when O-CSI is sent to VLR/GMSC.
-- They may only be included in ATSI/ATM ack/NSDC message.
-- O-CSI shall not be segmented.

O-BcsmCamelTDPDataList ::= SEQUENCE SIZE (1..maxNumOfCamelTDPData) OF
	O-BcsmCamelTDPData
	-- O-BcsmCamelTDPDataList shall not contain more than one instance of
	-- O-BcsmCamelTDPData containing the same value for o-BcsmTriggerDetectionPoint.
	-- For CAMEL Phase 2, this means that only one instance of O-BcsmCamelTDPData is allowed
	-- with o-BcsmTriggerDetectionPoint being equal to DP2.

maxNumOfCamelTDPData INTEGER ::= 10

O-BcsmCamelTDPData ::= SEQUENCE {
	o-BcsmTriggerDetectionPoint O-BcsmTriggerDetectionPoint,
	serviceKey ServiceKey,
	gsmSCF-Address [0] ISDN-AddressString,
	defaultCallHandling [1] DefaultCallHandling,
	--unused:extensionContainer [2] ExtensionContainer OPTIONAL,
	...
	}

ServiceKey ::= INTEGER (0..2147483647)

O-BcsmTriggerDetectionPoint ::= ENUMERATED {
	collectedInfo (2),
	...,
	routeSelectFailure (4) }
	-- exception handling:
	-- For O-BcsmCamelTDPData sequences containing this parameter with any
	-- other value than the ones listed the receiver shall ignore the whole
	-- O-BcsmCamelTDPDatasequence.
	-- For O-BcsmCamelTDP-Criteria sequences containing this parameter with any
	-- other value than the ones listed the receiver shall ignore the whole
	-- O-BcsmCamelTDP-Criteria sequence.

O-BcsmCamelTDPCriteriaList ::= SEQUENCE SIZE (1..maxNumOfCamelTDPData) OF
	O-BcsmCamelTDP-Criteria

T-BCSM-CAMEL-TDP-CriteriaList ::= SEQUENCE SIZE (1..maxNumOfCamelTDPData) OF
	T-BCSM-CAMEL-TDP-Criteria

O-BcsmCamelTDP-Criteria ::= SEQUENCE {
	o-BcsmTriggerDetectionPoint O-BcsmTriggerDetectionPoint,
	destinationNumberCriteria [0] DestinationNumberCriteria OPTIONAL,
	basicServiceCriteria [1] BasicServiceCriteria OPTIONAL,
	callTypeCriteria [2] CallTypeCriteria OPTIONAL,
	...,
	o-CauseValueCriteria [3] O-CauseValueCriteria OPTIONAL,
	extensionContainer [4] ExtensionContainer OPTIONAL }

T-BCSM-CAMEL-TDP-Criteria ::= SEQUENCE {
	t-BCSM-TriggerDetectionPoint T-BcsmTriggerDetectionPoint,
	basicServiceCriteria [0] BasicServiceCriteria OPTIONAL,
	t-CauseValueCriteria [1] T-CauseValueCriteria OPTIONAL,
	... }

DestinationNumberCriteria ::= SEQUENCE {
	matchType [0] MatchType,
	destinationNumberList [1] DestinationNumberList OPTIONAL,
	destinationNumberLengthList [2] DestinationNumberLengthList OPTIONAL,
	-- one or both of destinationNumberList and destinationNumberLengthList
	-- shall be present
	...}

DestinationNumberList ::= SEQUENCE SIZE (1..maxNumOfCamelDestinationNumbers) OF
	ISDN-AddressString
	-- The receiving entity shall not check the format of a number in
	-- the dialled number list

DestinationNumberLengthList ::= SEQUENCE SIZE (1..maxNumOfCamelDestinationNumberLengths) OF
	INTEGER(1..maxNumOfISDN-AddressDigits)

BasicServiceCriteria ::= SEQUENCE SIZE(1..maxNumOfCamelBasicServiceCriteria) OF
	Ext-BasicServiceCode

maxNumOfISDN-AddressDigits INTEGER ::= 15

maxNumOfCamelDestinationNumbers INTEGER ::= 10

maxNumOfCamelDestinationNumberLengths INTEGER ::= 3

maxNumOfCamelBasicServiceCriteria INTEGER ::= 5

CallTypeCriteria ::= ENUMERATED {
	forwarded (0),
	notForwarded (1)}

MatchType ::= ENUMERATED {
	inhibiting (0),
	enabling (1)}

O-CauseValueCriteria ::= SEQUENCE SIZE(1..maxNumOfCAMEL-O-CauseValueCriteria) OF
	CauseValue

T-CauseValueCriteria ::= SEQUENCE SIZE(1..maxNumOfCAMEL-T-CauseValueCriteria) OF
	CauseValue

maxNumOfCAMEL-O-CauseValueCriteria INTEGER ::= 5

maxNumOfCAMEL-T-CauseValueCriteria INTEGER ::= 5

CauseValue ::= OCTET STRING (SIZE(1))
	-- Type extracted from Cause parameter in ITU-T Recommendation Q.763.
	-- For the use of cause value refer to ITU-T Recommendation Q.850.

DefaultCallHandling ::= ENUMERATED {
	continueCall (0) ,
	releaseCall (1) ,
	...}
	-- exception handling:
	-- reception of values in range 2-31 shall be treated as "continueCall"
	-- reception of values greater than 31 shall be treated as "releaseCall"

CamelCapabilityHandling ::= INTEGER(1..16)
	-- value 1 = CAMEL phase 1,
	-- value 2 = CAMEL phase 2,
	-- value 3 = CAMEL Phase 3,
	-- value 4 = CAMEL phase 4:
	-- reception of values greater than 4 shall be treated as CAMEL phase 4.

SupportedCamelPhases ::= BIT STRING {
	phase1 (0),
	phase2 (1),
	phase3 (2),
	phase4 (3)} (SIZE (1..16))
-- A node shall mark in the BIT STRING all CAMEL Phases it supports.
-- Other values than listed above shall be discarded.

OfferedCamel4CSIs ::= BIT STRING {
    o-csi (0),
    d-csi (1),
    vt-csi (2),
    t-csi (3),
    mt-sms-csi (4),
    mg-csi (5),
    psi-enhancements (6)
    } (SIZE (7..16))
    -- A node supporting Camel phase 4 shall mark in the BIT STRING all Camel4 CSIs
    -- it offers.
    -- Other values than listed above shall be discarded.

--unused:OfferedCamel4Functionalities ::= BIT STRING {
--unused:    initiateCallAttempt (0),
--unused:    splitLeg (1),
--unused:    moveLeg (2),
--unused:    disconnectLeg (3),
--unused:    entityReleased (4),
--unused:    dfc-WithArgument (5),
--unused:    playTone (6),
--unused:    dtmf-MidCall (7),
--unused:    chargingIndicator (8),
--unused:    alertingDP (9),
--unused:    locationAtAlerting (10),
--unused:    changeOfPositionDP (11),
--unused:    or-Interactions (12),
--unused:    warningToneEnhancements (13),
--unused:    cf-Enhancements (14),
--unused:    subscribedEnhancedDialledServices (15),
--unused:    servingNetworkEnhancedDialledServices (16),
--unused:    criteriaForChangeOfPositionDP (17),
--unused:    serviceChangeDP (18),
--unused:    collectInformation (19)
--unused:    } (SIZE (15..64))
    -- A node supporting Camel phase 4 shall mark in the BIT STRING all CAMEL4
    -- functionalities it offers.
    -- Other values than listed above shall be discarded.

SMS-CSI ::= SEQUENCE {
    sms-CAMEL-TDP-DataList [0] SMS-CAMEL-TDP-DataList OPTIONAL,
    camelCapabilityHandling [1] CamelCapabilityHandling OPTIONAL,
    extensionContainer [2] ExtensionContainer OPTIONAL,
    notificationToCSE [3] NULL OPTIONAL,
    csi-Active [4] NULL OPTIONAL,
    ...}
    -- notificationToCSE and csi-Active shall not be present
    -- when MO-SMS-CSI or MT-SMS-CSI is sent to VLR or SGSN.
    -- They may only be included in ATSI/ATM ack/NSDC message.
    -- SMS-CAMEL-TDP-Data and camelCapabilityHandling shall be present in
    -- the SMS-CSI sequence.
    -- If SMS-CSI is segmented, sms-CAMEL-TDP-DataList and camelCapabilityHandling shall be
    -- present in the first segment

SMS-CAMEL-TDP-DataList ::= SEQUENCE SIZE (1..maxNumOfCamelTDPData) OF
    SMS-CAMEL-TDP-Data
    -- SMS-CAMEL-TDP-DataList shall not contain more than one instance of
    -- SMS-CAMEL-TDP-Data containing the same value for sms-TriggerDetectionPoint.

SMS-CAMEL-TDP-Data ::= SEQUENCE {
    sms-TriggerDetectionPoint [0] SMS-TriggerDetectionPoint,
    serviceKey [1] ServiceKey,
    gsmSCF-Address [2] ISDN-AddressString,
    defaultSMS-Handling [3] DefaultSMS-Handling,
    extensionContainer [4] ExtensionContainer OPTIONAL,
    ...
    }

SMS-TriggerDetectionPoint ::= ENUMERATED {
    sms-CollectedInfo (1),
    ...,
    sms-DeliveryRequest (2)
    }
    -- exception handling:
    -- For SMS-CAMEL-TDP-Data and MT-smsCAMELTDP-Criteria sequences containing this
    -- parameter with any other value than the ones listed the receiver shall ignore
    -- the whole sequence.
    --
    -- If this parameter is received with any other value than sms-CollectedInfo
    -- in an SMS-CAMEL-TDP-Data sequence contained in mo-sms-CSI, then the receiver shall
    -- ignore the whole SMS-CAMEL-TDP-Data sequence.
    --
    -- If this parameter is received with any other value than sms-DeliveryRequest
    -- in an SMS-CAMEL-TDP-Data sequence contained in mt-sms-CSI then the receiver shall
    -- ignore the whole SMS-CAMEL-TDP-Data sequence.
    --
    -- If this parameter is received with any other value than sms-DeliveryRequest
    -- in an MT-smsCAMELTDP-Criteria sequence then the receiver shall
    -- ignore the whole MT-smsCAMELTDP-Criteria sequence.

DefaultSMS-Handling ::= ENUMERATED {
    continueTransaction (0) ,
    releaseTransaction (1) ,
    ...}
    -- exception handling:
    -- reception of values in range 2-31 shall be treated as "continueTransaction"
    -- reception of values greater than 31 shall be treated as "releaseTransaction"

M-CSI ::= SEQUENCE {
	mobilityTriggers MobilityTriggers,
	serviceKey ServiceKey,
	gsmSCF-Address [0] ISDN-AddressString,
	extensionContainer [1] ExtensionContainer OPTIONAL,
	notificationToCSE [2] NULL OPTIONAL,
	csi-Active [3] NULL OPTIONAL,
	...}
-- notificationToCSE and csi-Active shall not be present when M-CSI is sent to VLR.
-- They may only be included in ATSI/ATM ack/NSDC message.

MG-CSI ::= SEQUENCE {
	mobilityTriggers MobilityTriggers,
	serviceKey ServiceKey,
	gsmSCF-Address [0] ISDN-AddressString,
	extensionContainer [1] ExtensionContainer OPTIONAL,
	notificationToCSE [2] NULL OPTIONAL,
	csi-Active [3] NULL OPTIONAL,
	...}
	-- notificationToCSE and csi-Active shall not be present when MG-CSI is sent to SGSN.
	-- They may only be included in ATSI/ATM ack/NSDC message.

MobilityTriggers ::= SEQUENCE SIZE (1..maxNumOfMobilityTriggers) OF
	MM-Code

maxNumOfMobilityTriggers INTEGER ::= 10

MM-Code ::= OCTET STRING (SIZE (1))
	-- This type is used to indicate a Mobility Management event.
	-- Actions for the following MM-Code values are defined in CAMEL Phase 4:
	--
	-- CS domain MM events:
	-- Location-update-in-same-VLR MM-Code ::= '00000000'B
	-- Location-update-to-other-VLR MM-Code ::= '00000001'B
	-- IMSI-Attach MM-Code ::= '00000010'B
	-- MS-initiated-IMSI-Detach MM-Code ::= '00000011'B
	-- Network-initiated-IMSI-Detach MM-Code ::= '00000100'B
	--
	-- PS domain MM events:
	-- Routeing-Area-update-in-same-SGSN MM-Code ::= '10000000'B
	-- Routeing-Area-update-to-other-SGSN-update-from-new-SGSN
	-- MM-Code ::= '10000001'B
	-- Routeing-Area-update-to-other-SGSN-disconnect-by-detach
	-- MM-Code ::= '10000010'B
	-- GPRS-Attach MM-Code ::= '10000011'B
	-- MS-initiated-GPRS-Detach MM-Code ::= '10000100'B
	-- Network-initiated-GPRS-Detach MM-Code ::= '10000101'B
	-- Network-initiated-transfer-to-MS-not-reachable-for-paging
	-- MM-Code ::= '10000110'B
	--
	-- If the MSC receives any other MM-code than the ones listed above for the
	-- CS domain, then the MSC shall ignore that MM-code.
	-- If the SGSN receives any other MM-code than the ones listed above for the
	-- PS domain, then the SGSN shall ignore that MM-code.

T-CSI ::= SEQUENCE {
	t-BcsmCamelTDPDataList T-BcsmCamelTDPDataList,
	extensionContainer ExtensionContainer OPTIONAL,
	...,
	camelCapabilityHandling [0] CamelCapabilityHandling OPTIONAL,
	notificationToCSE [1] NULL OPTIONAL,
	csi-Active [2] NULL OPTIONAL}
-- notificationToCSE and csi-Active shall not be present when VT-CSI/T-CSI is sent
-- to VLR/GMSC.
-- They may only be included in ATSI/ATM ack/NSDC message.
-- T-CSI shall not be segmented.

T-BcsmCamelTDPDataList ::= SEQUENCE SIZE (1..maxNumOfCamelTDPData) OF
	T-BcsmCamelTDPData
	--- T-BcsmCamelTDPDataList shall not contain more than one instance of
	--- T-BcsmCamelTDPData containing the same value for t-BcsmTriggerDetectionPoint.
	--- For CAMEL Phase 2, this means that only one instance of T-BcsmCamelTDPData is allowed
	--- with t-BcsmTriggerDetectionPoint being equal to DP12.
	--- For CAMEL Phase 3, more TDP’s are allowed.

T-BcsmCamelTDPData ::= SEQUENCE {
	t-BcsmTriggerDetectionPoint T-BcsmTriggerDetectionPoint,
	serviceKey ServiceKey,
	gsmSCF-Address [0] ISDN-AddressString,
	defaultCallHandling [1] DefaultCallHandling,
	extensionContainer [2] ExtensionContainer OPTIONAL,
	...}

T-BcsmTriggerDetectionPoint ::= ENUMERATED {
	termAttemptAuthorized (12),
	... ,
	tBusy (13),
	tNoAnswer (14)}
	-- exception handling:
	-- For T-BcsmCamelTDPData sequences containing this parameter with any other
	-- value than the ones listed above, the receiver shall ignore the whole
	-- T-BcsmCamelTDPData sequence.
	
-- gprs location information retrieval types

SendRoutingInfoForGprsArg ::= SEQUENCE {
	imsi [0] IMSI,
	ggsn-Address [1] GSN-Address OPTIONAL,
	ggsn-Number [2] ISDN-AddressString,
	--unused:extensionContainer [3] ExtensionContainer OPTIONAL,
	...}

SendRoutingInfoForGprsRes ::= SEQUENCE {
	sgsn-Address [0] GSN-Address,
	ggsn-Address [1] GSN-Address OPTIONAL,
	mobileNotReachableReason [2] AbsentSubscriberDiagnosticSM OPTIONAL,
	--unused:extensionContainer [3] ExtensionContainer OPTIONAL,
	...}

-- failure report types

FailureReportArg ::= SEQUENCE {
	imsi [0] IMSI,
	ggsn-Number [1] ISDN-AddressString , --unused
	--unused:ggsn-Address [2] GSN-Address OPTIONAL,
	--unused:extensionContainer [3] ExtensionContainer OPTIONAL,
	...}

--unused:FailureReportRes ::= SEQUENCE {
--unused:	ggsn-Address [0] GSN-Address OPTIONAL,
--unused:	extensionContainer [1] ExtensionContainer OPTIONAL,
--unused:	...}

-- gprs notification types

NoteMsPresentForGprsArg ::= SEQUENCE {
	imsi [0] IMSI,
	sgsn-Address [1] GSN-Address, --unused
	--unused:ggsn-Address [2] GSN-Address OPTIONAL,
	--unused:extensionContainer [3] ExtensionContainer OPTIONAL,
	...}

--unused:NoteMsPresentForGprsRes ::= SEQUENCE {
--unused:	extensionContainer [0] ExtensionContainer OPTIONAL,
--unused:	...}

-- fault recovery types

--unused:ResetArg ::= SEQUENCE {
--unused:	hlr-Number ISDN-AddressString,
--unused:	hlr-List HLR-List OPTIONAL,
--unused:	...}

RestoreDataArg ::= SEQUENCE {
	imsi IMSI,
	lmsi LMSI OPTIONAL,
	extensionContainer ExtensionContainer OPTIONAL,
	...,
	vlr-Capability [6] VLR-Capability OPTIONAL,
	restorationIndicator [7] NULL OPTIONAL
	}

RestoreDataRes ::= SEQUENCE {
	hlr-Number ISDN-AddressString,
	msNotReachable NULL OPTIONAL,
	extensionContainer ExtensionContainer OPTIONAL,
	...}

-- VBS/VGCS types

VBSDataList ::= SEQUENCE SIZE (1..maxNumOfVBSGroupIds) OF
	VoiceBroadcastData

VGCSDataList ::= SEQUENCE SIZE (1..maxNumOfVGCSGroupIds) OF
	VoiceGroupCallData

maxNumOfVBSGroupIds INTEGER ::= 50

maxNumOfVGCSGroupIds INTEGER ::= 50

VoiceGroupCallData ::= SEQUENCE {
	groupId GroupId,
	-- groupId shall be filled with six TBCD fillers (1111)if the longGroupId is present
	--unused:extensionContainer ExtensionContainer OPTIONAL,
	... --unused:,
	--unused:additionalSubscriptions AdditionalSubscriptions OPTIONAL,
	--unused:additionalInfo [0] AdditionalInfo OPTIONAL,
	--unused:longGroupId [1] Long-GroupId OPTIONAL-- }
	-- VoiceGroupCallData containing a longGroupId shall not be sent to VLRs that did not
	-- indicate support of long Group IDs within the Update Location or Restore Data
	-- request message

--unused:AdditionalInfo ::= BIT STRING (SIZE (1..136))
   -- Refers to Additional Info as specified in 3GPP TS 43.068

--unused:AdditionalSubscriptions ::= BIT STRING {
--unused:    privilegedUplinkRequest (0),
--unused:    emergencyUplinkRequest (1),
--unused:    emergencyReset (2)} (SIZE (3..8))
    -- Other bits than listed above shall be discarded.

VoiceBroadcastData ::= SEQUENCE {
    groupid GroupId,
    -- groupId shall be filled with six TBCD fillers (1111)if the longGroupId is present
    --unused:broadcastInitEntitlement NULL OPTIONAL,
    --unused:extensionContainer ExtensionContainer OPTIONAL,
    ... --unused:,
    --unused:longGroupId [0] Long-GroupId OPTIONAL-- }
    -- VoiceBroadcastData containing a longGroupId shall not be sent to VLRs that did not
    -- indicate support of long Group IDs within the Update Location or Restore Data
    -- request message

GroupId ::= TBCD-STRING (SIZE (3))
	-- When Group-Id is less than six characters in length, the TBCD filler (1111)
	-- is used to fill unused half octets.
	-- Refers to the Group Identification as specified in 3GPP TS 23.003
	-- and 3GPP TS 43.068/ 43.069

Long-GroupId ::= TBCD-STRING (SIZE (4))
	-- When Long-Group-Id is less than eight characters in length, the TBCD filler (1111)
	-- is used to fill unused half octets.
	-- Refers to the Group Identification as specified in 3GPP TS 23.003
	-- and 3GPP TS 43.068/ 43.069
	
-- provide subscriber info types

ProvideSubscriberInfoArg ::= SEQUENCE {
	imsi [0] IMSI,
	lmsi [1] LMSI OPTIONAL,
	requestedInfo [2] RequestedInfo,  --unused:
	--unused:extensionContainer [3] ExtensionContainer OPTIONAL,
	...--unused:,
	--unused:callPriority [4] EMLPP-Priority OPTIONAL
	}

ProvideSubscriberInfoRes ::= SEQUENCE {
	subscriberInfo SubscriberInfo,
	--unused:extensionContainer ExtensionContainer OPTIONAL,
	...}

SubscriberInfo ::= SEQUENCE {
    locationInformation [0] LocationInformation OPTIONAL,
    subscriberState [1] SubscriberState OPTIONAL,                               --unused
    extensionContainer [2] ExtensionContainer OPTIONAL,                         --unused
    ... ,
    locationInformationGPRS [3] LocationInformationGPRS OPTIONAL,               --unused
    ps-SubscriberState [4] PS-SubscriberState OPTIONAL,                         --unused
    imei [5] IMEI OPTIONAL,
    ms-Classmark2 [6] MS-Classmark2 OPTIONAL,                                   --unused
    gprs-MS-Class [7] GPRSMSClass OPTIONAL,                                     --unused
    mnpInfoRes [8] MNPInfoRes OPTIONAL,
    imsVoiceOverPS-SessionsIndication [9] IMS-VoiceOverPS-SessionsInd OPTIONAL, --unused
    lastUE-ActivityTime [10] Time OPTIONAL,                                     --unused
    lastRAT-Type [11] Used-RAT-Type OPTIONAL,                                   --unused
    eps-SubscriberState [12] PS-SubscriberState OPTIONAL,                       --unused
    locationInformationEPS [13] LocationInformationEPS OPTIONAL                 --unused-- }
    -- If the HLR receives locationInformation, subscriberState or ms-Classmark2 from an SGSN or
    -- MME (via an IWF), it shall discard them.
    -- If the HLR receives locationInformationGPRS, ps-SubscriberState, gprs-MS-Class or
    -- locationInformationEPS (outside the locationInformation IE) from a VLR, it shall
    -- discard them.
    -- If the HLR receives parameters which it has not requested, it shall discard them.

IMS-VoiceOverPS-SessionsInd ::= ENUMERATED {
    imsVoiceOverPS-SessionsNotSupported (0),
    imsVoiceOverPS-SessionsSupported (1),
    unknown (2)
    }
    -- "unknown" shall not be used within ProvideSubscriberInfoRes

MNPInfoRes ::= SEQUENCE {
    routeingNumber [0] RouteingNumber OPTIONAL, --unused
    imsi [1] IMSI OPTIONAL,
    msisdn [2] ISDN-AddressString OPTIONAL,
    --unused:numberPortabilityStatus [3] NumberPortabilityStatus OPTIONAL,
    --unused:extensionContainer [4] ExtensionContainer OPTIONAL,
    ... }
    -- The IMSI parameter contains a generic IMSI, i.e. it is not tied necessarily to the
    -- Subscriber. MCC and MNC values in this IMSI shall point to the Subscription Network of
    -- the Subscriber. See 3GPP TS 23.066 [108].

RouteingNumber ::= TBCD-STRING (SIZE (1..5))

NumberPortabilityStatus ::= ENUMERATED {
	notKnownToBePorted (0),
	ownNumberPortedOut (1),
	foreignNumberPortedToForeignNetwork (2),
	...,
	ownNumberNotPortedOut (4),
	foreignNumberPortedIn (5)
	}
	-- exception handling:
	-- reception of other values than the ones listed the receiver shall ignore the
	-- whole NumberPortabilityStatus;
	-- ownNumberNotPortedOut or foreignNumberPortedIn may only be included in Any Time
	-- Interrogation message.

MS-Classmark2 ::= OCTET STRING (SIZE (3))
	-- This parameter carries the value part of the MS Classmark 2 IE defined in
	-- 3GPP TS 24.008 [35].

GPRSMSClass ::= SEQUENCE {
	mSNetworkCapability [0] MSNetworkCapability,
	mSRadioAccessCapability [1] MSRadioAccessCapability OPTIONAL
	}

MSNetworkCapability ::= OCTET STRING (SIZE (1..8))
	-- This parameter carries the value part of the MS Network Capability IE defined in
	-- 3GPP TS 24.008 [35].

MSRadioAccessCapability ::= OCTET STRING (SIZE (1..50))
	-- This parameter carries the value part of the MS Radio Access Capability IE defined in
	-- 3GPP TS 24.008 [35].

RequestedInfo ::= SEQUENCE {
	locationInformation [0] NULL OPTIONAL,
	subscriberState [1] NULL OPTIONAL,
	extensionContainer [2] ExtensionContainer OPTIONAL,
	...,
	currentLocation [3] NULL OPTIONAL,
	requestedDomain [4] DomainType OPTIONAL,
	imei [6] NULL OPTIONAL,
	ms-classmark [5] NULL OPTIONAL,
	mnpRequestedInfo [7] NULL OPTIONAL,
	t-adsData [8] NULL OPTIONAL,
	requestedNodes [9] RequestedNodes OPTIONAL,
	servingNodeIndication [10] NULL OPTIONAL }
	-- currentLocation shall be absent if locationInformation is absent
	-- t-adsData shall be absent in messages sent to the VLR
	-- requestedNodes shall be absent if requestedDomain is "cs-Domain"
	-- servingNodeIndication shall be absent if locationInformation is absent;
	-- servingNodeIndication shall be absent if current location is present;
	-- servingNodeIndication indicates by its presence that only the serving node's
	-- address (MME-Name or SGSN-Number or VLR-Number) is requested.

DomainType ::= ENUMERATED {
	cs-Domain (0),
	ps-Domain (1),
	...}
	-- exception handling:
	-- reception of values > 1 shall be mapped to 'cs-Domain'

RequestedNodes ::= BIT STRING {
	mme (0),
	sgsn (1)} (SIZE (1..8))
	-- Other bits than listed above shall be discarded.

LocationInformation ::= SEQUENCE {
	ageOfLocationInformation AgeOfLocationInformation OPTIONAL,
	geographicalInformation [0] GeographicalInformation OPTIONAL,
	vlr-number [1] ISDN-AddressString OPTIONAL,
	locationNumber [2] LocationNumber OPTIONAL,
	cellGlobalIdOrServiceAreaIdOrLAI [3] CellGlobalIdOrServiceAreaIdOrLAI OPTIONAL,
	extensionContainer [4] ExtensionContainer OPTIONAL,
	... ,
	selectedLSA-Id [5] LSAIdentity OPTIONAL,
	msc-Number [6] ISDN-AddressString OPTIONAL,
	geodeticInformation [7] GeodeticInformation OPTIONAL,
	currentLocationRetrieved [8] NULL OPTIONAL,
	sai-Present [9] NULL OPTIONAL,
	locationInformationEPS [10] LocationInformationEPS OPTIONAL,
	userCSGInformation [11] UserCSGInformation OPTIONAL }
	-- sai-Present indicates that the cellGlobalIdOrServiceAreaIdOrLAI parameter contains
	-- a Service Area Identity.
	-- currentLocationRetrieved shall be present
	-- if the location information were retrieved after a successfull paging.
	-- if the locationinformationEPS IE is present then the cellGlobalIdOrServiceAreaIdOrLAI IE,
	-- the ageOfLocationInformation IE, the geographicalInformation IE, the geodeticInformation IE
	-- and the currentLocationRetrieved IE (outside the locationInformationEPS IE) shall be
	-- absent.
	-- UserCSGInformation contains the CSG ID, Access mode, and the CSG Membership Indication in
	-- the case the Access mode is Hybrid Mode.

LocationInformationEPS ::= SEQUENCE {
	e-utranCellGlobalIdentity [0] E-UTRAN-CGI OPTIONAL,
	trackingAreaIdentity [1] TA-Id OPTIONAL,
	extensionContainer [2] ExtensionContainer OPTIONAL,
	geographicalInformation [3] GeographicalInformation OPTIONAL,
	geodeticInformation [4] GeodeticInformation OPTIONAL,
	currentLocationRetrieved [5] NULL OPTIONAL,
	ageOfLocationInformation [6] AgeOfLocationInformation OPTIONAL,
	...,
	mme-Name [7] DiameterIdentity OPTIONAL }
	-- currentLocationRetrieved shall be present if the location information
	-- was retrieved after successful paging.

LocationInformationGPRS ::= SEQUENCE {
	cellGlobalIdOrServiceAreaIdOrLAI [0] CellGlobalIdOrServiceAreaIdOrLAI OPTIONAL,
	routeingAreaIdentity [1] RAIdentity OPTIONAL,
	geographicalInformation [2] GeographicalInformation OPTIONAL,
	sgsn-Number [3] ISDN-AddressString OPTIONAL,
	selectedLSAIdentity [4] LSAIdentity OPTIONAL,
	extensionContainer [5] ExtensionContainer OPTIONAL,
	...,
	sai-Present [6] NULL OPTIONAL,
	geodeticInformation [7] GeodeticInformation OPTIONAL,
	currentLocationRetrieved [8] NULL OPTIONAL,
	ageOfLocationInformation [9] AgeOfLocationInformation OPTIONAL,
	userCSGInformation [10] UserCSGInformation OPTIONAL }
	-- sai-Present indicates that the cellGlobalIdOrServiceAreaIdOrLAI parameter contains
	-- a Service Area Identity.
	-- currentLocationRetrieved shall be present if the location information
	-- was retrieved after successful paging.
	-- UserCSGInformation contains the CSG ID, Access mode, and the CSG Membership Indication in
	-- the case the Access mode is Hybrid Mode.

UserCSGInformation ::= SEQUENCE {
	csg-Id [0] CSG-Id,
	extensionContainer [1] ExtensionContainer OPTIONAL,
	...,
	accessMode [2] OCTET STRING (SIZE(1)) OPTIONAL,
	cmi [3] OCTET STRING (SIZE(1)) OPTIONAL }
	-- The encoding of the accessMode and cmi parameters are as defined in 3GPP TS 29.060 [105].

GeographicalInformation ::= OCTET STRING (SIZE (8))
    -- Refers to geographical Information defined in 3GPP TS 23.032.
    -- Only the description of an ellipsoid point with uncertainty circle
    -- as specified in 3GPP TS 23.032 is allowed to be used
    -- The internal structure according to 3GPP TS 23.032 is as follows:
    -- Type of shape (ellipsoid point with uncertainty circle) 1 octet
    -- Degrees of Latitude 3 octets
    -- Degrees of Longitude 3 octets
    -- Uncertainty code 1 octet

GeodeticInformation ::= OCTET STRING (SIZE (10))
    -- Refers to Calling Geodetic Location defined in Q.763 (1999).
    -- Only the description of an ellipsoid point with uncertainty circle
    -- as specified in Q.763 (1999) is allowed to be used
    -- The internal structure according to Q.763 (1999) is as follows:
    -- Screening and presentation indicators 1 octet
    -- Type of shape (ellipsoid point with uncertainty circle) 1 octet
    -- Degrees of Latitude 3 octets
    -- Degrees of Longitude 3 octets
    -- Uncertainty code 1 octet
    -- Confidence 1 octet

LocationNumber ::= OCTET STRING (SIZE (2..10))
    -- the internal structure is defined in ITU-T Rec Q.763

SubscriberState ::= CHOICE {
    assumedIdle [0] NULL,
    camelBusy [1] NULL,
    netDetNotReachable NotReachableReason,
    notProvidedFromVLR [2] NULL}

PS-SubscriberState ::= CHOICE {
    notProvidedFromSGSNorMME [0] NULL,
    ps-Detached [1] NULL,
    ps-AttachedNotReachableForPaging [2] NULL,
    ps-AttachedReachableForPaging [3] NULL,
    ps-PDP-ActiveNotReachableForPaging [4] PDP-ContextInfoList,
    ps-PDP-ActiveReachableForPaging [5] PDP-ContextInfoList,
    netDetNotReachable NotReachableReason }

PDP-ContextInfoList ::= SEQUENCE SIZE (1..maxNumOfPDP-Contexts) OF
    PDP-ContextInfo
    PDP-ContextInfo ::= SEQUENCE {
    pdp-ContextIdentifier [0] ContextId,
    pdp-ContextActive [1] NULL OPTIONAL,
    pdp-Type [2] PDP-Type,
    pdp-Address [3] PDP-Address OPTIONAL,
    apn-Subscribed [4] APN OPTIONAL,
    apn-InUse [5] APN OPTIONAL,
    nsapi [6] NSAPI OPTIONAL,
    transactionId [7] TransactionId OPTIONAL,
    teid-ForGnAndGp [8] TEID OPTIONAL,
    teid-ForIu [9] TEID OPTIONAL,
    ggsn-Address [10] GSN-Address OPTIONAL,
    qos-Subscribed [11] Ext-QoS-Subscribed OPTIONAL,
    qos-Requested [12] Ext-QoS-Subscribed OPTIONAL,
    qos-Negotiated [13] Ext-QoS-Subscribed OPTIONAL,
    chargingId [14] GPRSChargingID OPTIONAL,
    chargingCharacteristics [15] ChargingCharacteristics OPTIONAL,
    rnc-Address [16] GSN-Address OPTIONAL,
    extensionContainer [17] ExtensionContainer OPTIONAL,
    ...,
    qos2-Subscribed [18] Ext2-QoS-Subscribed OPTIONAL,
    -- qos2-Subscribed may be present only if qos-Subscribed is present.
    qos2-Requested [19] Ext2-QoS-Subscribed OPTIONAL,
    -- qos2-Requested may be present only if qos-Requested is present.
    qos2-Negotiated [20] Ext2-QoS-Subscribed OPTIONAL,
    -- qos2-Negotiated may be present only if qos-Negotiated is present.
    qos3-Subscribed [21] Ext3-QoS-Subscribed OPTIONAL,
    -- qos3-Subscribed may be present only if qos2-Subscribed is present.
    qos3-Requested [22] Ext3-QoS-Subscribed OPTIONAL,
    -- qos3-Requested may be present only if qos2-Requested is present.
    qos3-Negotiated [23] Ext3-QoS-Subscribed OPTIONAL,
    -- qos3-Negotiated may be present only if qos2-Negotiated is present.
    qos4-Subscribed [25] Ext4-QoS-Subscribed OPTIONAL,
    -- qos4-Subscribed may be present only if qos3-Subscribed is present.
    qos4-Requested [26] Ext4-QoS-Subscribed OPTIONAL,
    -- qos4-Requested may be present only if qos3-Requested is present.
    qos4-Negotiated [27] Ext4-QoS-Subscribed OPTIONAL,
    -- qos4-Negotiated may be present only if qos3-Negotiated is present.
    ext-pdp-Type [28] Ext-PDP-Type OPTIONAL,
    -- contains the value IPv4v6 defined in 3GPP TS 29.060 [105], if the PDP can be
    -- accessed by dual-stack UEs.
    ext-pdp-Address [29] PDP-Address OPTIONAL
    -- contains an additional IP address in case of dual-stack static IP address assignment
    -- for the UE.
    -- it may contain an IPv4 or an IPv6 address/prefix, and it may be present
    -- only if pdp-Address is present; if both are present, each parameter shall
    -- contain a different type of address (IPv4 or IPv6).
    }

NSAPI ::= INTEGER (0..15)
	-- This type is used to indicate the Network layer Service Access Point

TransactionId ::= OCTET STRING (SIZE (1..2))
	-- This type carries the value part of the transaction identifier which is used in the
	-- session management messages on the access interface. The encoding is defined in
	-- 3GPP TS 24.008

TEID ::= OCTET STRING (SIZE (4))
	-- This type carries the value part of the Tunnel Endpoint Identifier which is used to
	-- distinguish between different tunnels between the same pair of entities which communicate
	-- using the GPRS Tunnelling Protocol The encoding is defined in 3GPP TS 29.060.

GPRSChargingID ::= OCTET STRING (SIZE (4))
	-- The Charging ID is a unique four octet value generated by the GGSN when
	-- a PDP Context is activated. A Charging ID is generated for each activated context.
	-- The encoding is defined in 3GPP TS 29.060.

NotReachableReason ::= ENUMERATED {
	msPurged (0),
	imsiDetached (1),
	restrictedArea (2),
	notRegistered (3)
}

-- any time interrogation info types

AnyTimeInterrogationArg ::= SEQUENCE {
	subscriberIdentity [0] SubscriberIdentity,
	requestedInfo [1] RequestedInfo,           --unused
	gsmSCF-Address [3] ISDN-AddressString,     --unused
	--unused:extensionContainer [2] ExtensionContainer OPTIONAL,
	...}

AnyTimeInterrogationRes ::= SEQUENCE {
	subscriberInfo SubscriberInfo,
	--unused:extensionContainer ExtensionContainer OPTIONAL,
	...}

-- any time information handling types

AnyTimeSubscriptionInterrogationArg ::= SEQUENCE {
	subscriberIdentity [0] SubscriberIdentity,
	requestedSubscriptionInfo [1] RequestedSubscriptionInfo, --unused
	gsmSCF-Address [2] ISDN-AddressString,                   --unused
	--unused:extensionContainer [3] ExtensionContainer OPTIONAL,
	--unused:longFTN-Supported [4] NULL OPTIONAL,
	...}

AnyTimeSubscriptionInterrogationRes ::= SEQUENCE {
	callForwardingData [1] CallForwardingData OPTIONAL,
	callBarringData [2] CallBarringData OPTIONAL,                 --unused
	odb-Info [3] ODB-Info OPTIONAL,                               --unused
	camel-SubscriptionInfo [4] CAMEL-SubscriptionInfo OPTIONAL,   --unused
	supportedVLR-CAMEL-Phases [5] SupportedCamelPhases OPTIONAL,  --unused
	supportedSGSN-CAMEL-Phases [6] SupportedCamelPhases OPTIONAL, --unused
	extensionContainer [7] ExtensionContainer OPTIONAL,           --unused
	... ,
	offeredCamel4CSIsInVLR [8] OfferedCamel4CSIs OPTIONAL,        --unused
	offeredCamel4CSIsInSGSN [9] OfferedCamel4CSIs OPTIONAL,       --unused
	msisdn-BS-List [10] MSISDN-BS-List OPTIONAL,                  ...
	--unused:csg-SubscriptionDataList [11] CSG-SubscriptionDataList OPTIONAL,
	--unused:cw-Data [12] CallWaitingData OPTIONAL,
	--unused:ch-Data [13] CallHoldData OPTIONAL,
	--unused:clip-Data [14] ClipData OPTIONAL,
	--unused:clir-Data [15] ClirData OPTIONAL,
	--unused:ect-data [16] EctData OPTIONAL-- }

--unused:CallWaitingData ::= SEQUENCE {
--unused:	cwFeatureList [1] Ext-CwFeatureList,
--unused:	notificationToCSE [2] NULL OPTIONAL,
--unused:	... }
--unused:
--unused:Ext-CwFeatureList ::= SEQUENCE SIZE (1..maxNumOfExt-BasicServiceGroups) OF
--unused:	Ext-CwFeature
--unused:
--unused:Ext-CwFeature ::= SEQUENCE {
--unused:	basicService [1] Ext-BasicServiceCode,
--unused:	ss-Status [2] Ext-SS-Status,
--unused:	... }

--unused:ClipData ::= SEQUENCE {
--unused:	ss-Status [1] Ext-SS-Status,
--unused:	overrideCategory [2] OverrideCategory,
--unused:	notificationToCSE [3] NULL OPTIONAL,
--unused:	... }

--unused:ClirData ::= SEQUENCE {
--unused:	ss-Status [1] Ext-SS-Status,
--unused:	cliRestrictionOption [2] CliRestrictionOption OPTIONAL,
--unused:	notificationToCSE [3] NULL OPTIONAL,
--unused:	... }

--unused:CallHoldData ::= SEQUENCE {
--unused:	ss-Status [1] Ext-SS-Status,
--unused:	notificationToCSE [2] NULL OPTIONAL,
--unused:	... }

--unused:EctData ::= SEQUENCE {
--unused:	ss-Status [1] Ext-SS-Status,
--unused:	notificationToCSE [2] NULL OPTIONAL,
--unused:	... }

RequestedSubscriptionInfo ::= SEQUENCE {
    requestedSS-Info [1] SS-ForBS-Code OPTIONAL,
    odb [2] NULL OPTIONAL,
    requestedCAMEL-SubscriptionInfo [3] RequestedCAMEL-SubscriptionInfo OPTIONAL,
    supportedVLR-CAMEL-Phases [4] NULL OPTIONAL,
    supportedSGSN-CAMEL-Phases [5] NULL OPTIONAL,
    extensionContainer [6] ExtensionContainer OPTIONAL,
    ...,
    additionalRequestedCAMEL-SubscriptionInfo
    [7] AdditionalRequestedCAMEL-SubscriptionInfo
    OPTIONAL,
    msisdn-BS-List [8] NULL OPTIONAL,
    csg-SubscriptionDataRequested [9] NULL OPTIONAL,
    cw-Info [10] NULL OPTIONAL,
    clip-Info [11] NULL OPTIONAL,
    clir-Info [12] NULL OPTIONAL,
    hold-Info [13] NULL OPTIONAL,
    ect-Info [14] NULL OPTIONAL }
    
MSISDN-BS-List ::= SEQUENCE SIZE (1..maxNumOfMSISDN) OF
    MSISDN-BS
    
maxNumOfMSISDN INTEGER ::= 50

MSISDN-BS ::= SEQUENCE {
    msisdn ISDN-AddressString,
    --unused:basicServiceList [0] BasicServiceList OPTIONAL,
    --unused:extensionContainer [1] ExtensionContainer OPTIONAL,
    ...}

RequestedCAMEL-SubscriptionInfo ::= ENUMERATED {
    o-CSI (0),
    t-CSI (1),
    vt-CSI (2),
    tif-CSI (3),
    gprs-CSI (4),
    mo-sms-CSI (5),
    ss-CSI (6),
    m-CSI (7),
    d-csi (8)}

AdditionalRequestedCAMEL-SubscriptionInfo ::= ENUMERATED {
    mt-sms-CSI (0),
    mg-csi (1),
    o-IM-CSI (2),
    d-IM-CSI (3),
    vt-IM-CSI (4),
    ...}
    -- exception handling: unknown values shall be discarded by the receiver.

CallForwardingData ::= SEQUENCE {
    forwardingFeatureList Ext-ForwFeatureList,
    notificationToCSE NULL OPTIONAL,
    --unused:extensionContainer [0] ExtensionContainer OPTIONAL,
    ...}

CallBarringData ::= SEQUENCE {
    callBarringFeatureList Ext-CallBarFeatureList,
    password Password OPTIONAL,
    wrongPasswordAttemptsCounter WrongPasswordAttemptsCounter OPTIONAL,
    notificationToCSE NULL OPTIONAL,
    extensionContainer ExtensionContainer OPTIONAL,
    ...}

WrongPasswordAttemptsCounter ::= INTEGER (0..4)

ODB-Info ::= SEQUENCE {
    odb-Data ODB-Data,
    notificationToCSE NULL OPTIONAL,
    extensionContainer ExtensionContainer OPTIONAL,
    ...}

CAMEL-SubscriptionInfo ::= SEQUENCE {
    o-CSI [0] O-CSI OPTIONAL,
    o-BcsmCamelTDP-CriteriaList [1] O-BcsmCamelTDPCriteriaList OPTIONAL,
    d-CSI [2] D-CSI OPTIONAL,
    t-CSI [3] T-CSI OPTIONAL,
    t-BCSM-CAMEL-TDP-CriteriaList [4] T-BCSM-CAMEL-TDP-CriteriaList OPTIONAL,
    vt-CSI [5] T-CSI OPTIONAL,
    vt-BCSM-CAMEL-TDP-CriteriaList [6] T-BCSM-CAMEL-TDP-CriteriaList OPTIONAL,
    tif-CSI [7] NULL OPTIONAL,
    tif-CSI-NotificationToCSE [8] NULL OPTIONAL,
    gprs-CSI [9] GPRS-CSI OPTIONAL,
    mo-sms-CSI [10] SMS-CSI OPTIONAL,
    ss-CSI [11] SS-CSI OPTIONAL,
    m-CSI [12] M-CSI OPTIONAL,
    extensionContainer [13] ExtensionContainer OPTIONAL,
    ...,
    specificCSIDeletedList [14] SpecificCSI-Withdraw OPTIONAL,
    mt-sms-CSI [15] SMS-CSI OPTIONAL,
    mt-smsCAMELTDP-CriteriaList [16] MT-smsCAMELTDP-CriteriaList OPTIONAL,
    mg-csi [17] MG-CSI OPTIONAL,
    o-IM-CSI [18] O-CSI OPTIONAL,
    o-IM-BcsmCamelTDP-CriteriaList [19] O-BcsmCamelTDPCriteriaList OPTIONAL,
    d-IM-CSI [20] D-CSI OPTIONAL,
    vt-IM-CSI [21] T-CSI OPTIONAL,
    vt-IM-BCSM-CAMEL-TDP-CriteriaList [22] T-BCSM-CAMEL-TDP-CriteriaList OPTIONAL
    }

AnyTimeModificationArg ::= SEQUENCE {
    subscriberIdentity [0] SubscriberIdentity,
    gsmSCF-Address [1] ISDN-AddressString,                                      --unused
    modificationRequestFor-CF-Info [2] ModificationRequestFor-CF-Info OPTIONAL,
    --unused:modificationRequestFor-CB-Info [3] ModificationRequestFor-CB-Info OPTIONAL,
    --unused:modificationRequestFor-CSI [4] ModificationRequestFor-CSI OPTIONAL,
    --unused:extensionContainer [5] ExtensionContainer OPTIONAL,
    --unused:longFTN-Supported [6] NULL OPTIONAL,
    ...--unused:,
    --unused:modificationRequestFor-ODB-data [7] ModificationRequestFor-ODB-data OPTIONAL,
    --unused:modificationRequestFor-IP-SM-GW-Data [8] ModificationRequestFor-IP-SM-GW-Data OPTIONAL,
    --unused:activationRequestForUE-reachability [9] RequestedServingNode OPTIONAL,
    --unused:modificationRequestFor-CSG [10] ModificationRequestFor-CSG OPTIONAL,
    --unused:modificationRequestFor-CW-Data [11] ModificationRequestFor-CW-Info OPTIONAL,
    --unused:modificationRequestFor-CLIP-Data [12] ModificationRequestFor-CLIP-Info OPTIONAL,
    --unused:modificationRequestFor-CLIR-Data [13] ModificationRequestFor-CLIR-Info OPTIONAL,
    --unused:modificationRequestFor-HOLD-Data [14] ModificationRequestFor-CH-Info OPTIONAL,
    --unused:modificationRequestFor-ECT-Data [15] ModificationRequestFor-ECT-Info OPTIONAL-- }

--unused:ModificationRequestFor-CW-Info ::= SEQUENCE {
--unused:    basicService [0] Ext-BasicServiceCode OPTIONAL,
--unused:    ss-Status [1] Ext-SS-Status OPTIONAL,
--unused:    modifyNotificationToCSE [2] ModificationInstruction OPTIONAL,
--unused:    extensionContainer [3] ExtensionContainer OPTIONAL,
--unused:    ...}

--unused:ModificationRequestFor-CH-Info ::= SEQUENCE {
--unused:    ss-Status [0] Ext-SS-Status OPTIONAL,
--unused:    modifyNotificationToCSE [1] ModificationInstruction OPTIONAL,
--unused:    extensionContainer [2] ExtensionContainer OPTIONAL,
--unused:    ...}

--unused:ModificationRequestFor-ECT-Info ::= SEQUENCE {
--unused:    ss-Status [0] Ext-SS-Status OPTIONAL,
--unused:    modifyNotificationToCSE [1] ModificationInstruction OPTIONAL,
--unused:    extensionContainer [2] ExtensionContainer OPTIONAL,
--unused:    ...}

--unused:ModificationRequestFor-CLIR-Info ::= SEQUENCE {
--unused:    ss-Status [0] Ext-SS-Status OPTIONAL,
--unused:    cliRestrictionOption [1] CliRestrictionOption OPTIONAL,
--unused:    modifyNotificationToCSE [2] ModificationInstruction OPTIONAL,
--unused:    extensionContainer [3] ExtensionContainer OPTIONAL,
--unused:    ...}

--unused:ModificationRequestFor-CLIP-Info ::= SEQUENCE {
--unused:    ss-Status [0] Ext-SS-Status OPTIONAL,
--unused:    overrideCategory [1] OverrideCategory OPTIONAL,
--unused:    modifyNotificationToCSE [2] ModificationInstruction OPTIONAL,
--unused:    extensionContainer [3] ExtensionContainer OPTIONAL,
--unused:    ...}

--unused:ModificationRequestFor-CSG ::= SEQUENCE {
--unused:    modifyNotificationToCSE [0] ModificationInstruction OPTIONAL,
--unused:    extensionContainer [1] ExtensionContainer OPTIONAL,
--unused:    ...}

--unused:RequestedServingNode ::= BIT STRING {
--unused:    mmeAndSgsn (0)} (SIZE (1..8))
--unused:    ServingNode ::= BIT STRING {
--unused:    mme (0),
--unused:    sgsn (1)} (SIZE (2..8))
    -- Other bits than listed above shall be discarded.

AnyTimeModificationRes ::= SEQUENCE {
    ss-InfoFor-CSE [0] Ext-SS-InfoFor-CSE OPTIONAL,
    --unused:camel-SubscriptionInfo [1] CAMEL-SubscriptionInfo OPTIONAL,
    --unused:extensionContainer [2] ExtensionContainer OPTIONAL,
    ...--unused:,
    --unused:odb-Info [3] ODB-Info OPTIONAL,
    --unused:cw-Data [4] CallWaitingData OPTIONAL,
    --unused:ch-Data [5] CallHoldData OPTIONAL,
    --unused:clip-Data [6] ClipData OPTIONAL,
    --unused:clir-Data [7] ClirData OPTIONAL,
    --unused:ect-data [8] EctData OPTIONAL,
    --unused:serviceCentreAddress [9] AddressString OPTIONAL
    }

ModificationRequestFor-CF-Info ::= SEQUENCE {
    ss-Code [0] SS-Code,
    basicService [1] Ext-BasicServiceCode OPTIONAL,
    ss-Status [2] Ext-SS-Status OPTIONAL,
    forwardedToNumber [3] AddressString OPTIONAL,
    forwardedToSubaddress [4] ISDN-SubaddressString OPTIONAL,
    noReplyConditionTime [5] Ext-NoRepCondTime OPTIONAL,
    modifyNotificationToCSE [6] ModificationInstruction OPTIONAL,
    extensionContainer [7] ExtensionContainer OPTIONAL,
    ...}

--unused:ModificationRequestFor-CB-Info ::= SEQUENCE {
--unused:    ss-Code [0] SS-Code,
--unused:    basicService [1] Ext-BasicServiceCode OPTIONAL,
--unused:    ss-Status [2] Ext-SS-Status OPTIONAL,
--unused:    password [3] Password OPTIONAL,
--unused:    wrongPasswordAttemptsCounter [4] WrongPasswordAttemptsCounter OPTIONAL,
--unused:    modifyNotificationToCSE [5] ModificationInstruction OPTIONAL,
--unused:    extensionContainer [6] ExtensionContainer OPTIONAL,
--unused:    ...}

--unused:ModificationRequestFor-ODB-data ::= SEQUENCE {
--unused:    odb-data [0] ODB-Data OPTIONAL,
--unused:    modifyNotificationToCSE [1] ModificationInstruction OPTIONAL,
--unused:    extensionContainer [2] ExtensionContainer OPTIONAL,
--unused:    ...}

--unused:ModificationRequestFor-CSI ::= SEQUENCE {
--unused:    requestedCamel-SubscriptionInfo [0] RequestedCAMEL-SubscriptionInfo,
--unused:    modifyNotificationToCSE [1] ModificationInstruction OPTIONAL,
--unused:    modifyCSI-State [2] ModificationInstruction OPTIONAL,
--unused:    extensionContainer [3] ExtensionContainer OPTIONAL,
--unused:    ...,
--unused:    additionalRequestedCAMEL-SubscriptionInfo
--unused:    [4] AdditionalRequestedCAMEL-SubscriptionInfo
--unused:    OPTIONAL }
    -- requestedCamel-SubscriptionInfo shall be discarded if
    -- additionalRequestedCAMEL-SubscriptionInfo is received

--unused:ModificationRequestFor-IP-SM-GW-Data ::= SEQUENCE {
--unused:    modifyRegistrationStatus [0] ModificationInstruction OPTIONAL,
--unused:    extensionContainer [1] ExtensionContainer OPTIONAL,
--unused:    ...}

ModificationInstruction ::= ENUMERATED {
    deactivate (0),
    activate (1)}

-- subscriber data modification notification types
NoteSubscriberDataModifiedArg ::= SEQUENCE {
    imsi IMSI,
    msisdn ISDN-AddressString,
    forwardingInfoFor-CSE [0] Ext-ForwardingInfoFor-CSE OPTIONAL,
    --unused:callBarringInfoFor-CSE [1] Ext-CallBarringInfoFor-CSE OPTIONAL,
    --unused:odb-Info [2] ODB-Info OPTIONAL,
    --unused:camel-SubscriptionInfo [3] CAMEL-SubscriptionInfo OPTIONAL,
    --unused:allInformationSent [4] NULL OPTIONAL,
    --unused:extensionContainer ExtensionContainer OPTIONAL,
    ...--unused:,
    --unused:ue-reachable [5] ServingNode OPTIONAL,
    --unused:csg-SubscriptionDataList [6] CSG-SubscriptionDataList OPTIONAL,
    --unused:cw-Data [7] CallWaitingData OPTIONAL,
    --unused:ch-Data [8] CallHoldData OPTIONAL,
    --unused:clip-Data [9] ClipData OPTIONAL,
    --unused:clir-Data [10] ClirData OPTIONAL,
    --unused:ect-data [11] EctData OPTIONAL-- }

--unused:NoteSubscriberDataModifiedRes ::= SEQUENCE {
--unused:    extensionContainer ExtensionContainer OPTIONAL,
--unused:    ...}

-- mobility management event notificatioon info types
NoteMM-EventArg::= SEQUENCE {
    serviceKey ServiceKey,
    eventMet [0] MM-Code,
    imsi [1] IMSI,
    msisdn [2] ISDN-AddressString,
    locationInformation [3] LocationInformation OPTIONAL,
    supportedCAMELPhases [5] SupportedCamelPhases OPTIONAL,
    extensionContainer [6] ExtensionContainer OPTIONAL,
    ...,
    locationInformationGPRS [7] LocationInformationGPRS OPTIONAL --unused:,
    --unused:offeredCamel4Functionalities [8] OfferedCamel4Functionalities OPTIONAL
    }

--unused:NoteMM-EventRes ::= SEQUENCE {
--unused:    extensionContainer ExtensionContainer OPTIONAL,
--unused:    ...}

Ext-SS-InfoFor-CSE ::= CHOICE {
    forwardingInfoFor-CSE [0] Ext-ForwardingInfoFor-CSE,
    callBarringInfoFor-CSE [1] Ext-CallBarringInfoFor-CSE
    }

Ext-ForwardingInfoFor-CSE ::= SEQUENCE {
    ss-Code [0] SS-Code,
    forwardingFeatureList [1] Ext-ForwFeatureList,
    --unused:notificationToCSE [2] NULL OPTIONAL,
    --unused:extensionContainer [3] ExtensionContainer OPTIONAL,
    ...}

Ext-CallBarringInfoFor-CSE ::= SEQUENCE {
    ss-Code [0] SS-Code,
    callBarringFeatureList [1] Ext-CallBarFeatureList,
    password [2] Password OPTIONAL,
    wrongPasswordAttemptsCounter [3] WrongPasswordAttemptsCounter OPTIONAL,
    notificationToCSE [4] NULL OPTIONAL,
    extensionContainer [5] ExtensionContainer OPTIONAL,
    ...}

END
