-- ETSI TS 129 002 V10.4.0 (2011-10)
-- 17.7.3 Call handling data types
 
MAP-CH-DataTypes {
   itu-t identified-organization (4) etsi (0) mobileDomain (0)
   gsm-Network (1) modules (3) map-CH-DataTypes (13) version13 (13)}

DEFINITIONS

IMPLICIT TAGS

::=

BEGIN

EXPORTS
	--unused:SendRoutingInfoArg,
	--unused:SendRoutingInfoRes,
	--unused:ProvideRoamingNumberArg,
	--unused:ProvideRoamingNumberRes,
	--unused:ResumeCallHandlingArg,
	--unused:ResumeCallHandlingRes,
	--unused:NumberOfForwarding,
	--unused:SuppressionOfAnnouncement,
	--unused:CallReferenceNumber,
	--unused:SetReportingStateArg,
	--unused:SetReportingStateRes,
	--unused:StatusReportArg,
	--unused:StatusReportRes,
	--unused:RemoteUserFreeArg,
	--unused:RemoteUserFreeRes,
	--unused:IST-AlertArg,
	--unused:IST-AlertRes,
	--unused:IST-CommandArg,
	--unused:IST-CommandRes,
	--unused:UU-Data,
	--unused:ReleaseResourcesArg,
	-- WS added exports needed by gsm_map.asn (extra asn1 file to handle older proto. ver.)
	RoutingInfo--unused:,
	--unused:CUG-CheckInfo- -unused:,
	--unused:ReleaseResourcesRes
;

IMPORTS
	SubscriberInfo,
	SupportedCamelPhases,
	OfferedCamel4CSIs,
	CUG-Interlock,
	O-CSI, 
	D-CSI,
	O-BcsmCamelTDPCriteriaList, 
	T-BCSM-CAMEL-TDP-CriteriaList,
	--unused:IST-SupportIndicator,
	IST-AlertTimerValue,
	T-CSI,
	NumberPortabilityStatus--unused:,
	--unused:PagingArea
FROM MAP-MS-DataTypes {
   itu-t identified-organization (4) etsi (0) mobileDomain (0)
   gsm-Network (1) modules (3) map-MS-DataTypes (11) version13 (13)}

	--unused:ForwardingOptions,
	SS-List,
	CCBS-Feature
FROM MAP-SS-DataTypes {
   itu-t identified-organization (4) etsi (0) mobileDomain (0)
   gsm-Network (1) modules (3) map-SS-DataTypes (14) version13 (13)}

	ISDN-AddressString,
	--unused:ISDN-SubaddressString,
	--unused:FTN-AddressString,
	ExternalSignalInfo,
	--unused:Ext-ExternalSignalInfo,
	IMSI,
	--unused:LMSI,
	Ext-BasicServiceCode,
	--unused:AlertingPattern,
	NAEA-PreferredCI--unused:,
	--unused:EMLPP-Priority
FROM MAP-CommonDataTypes {
   itu-t identified-organization (4) etsi (0) mobileDomain (0)
   gsm-Network (1) modules (3) map-CommonDataTypes (18) version13 (13)}

	ExtensionContainer
FROM MAP-ExtensionDataTypes {
   itu-t identified-organization (4) etsi (0) mobileDomain (0)
   gsm-Network (1) modules (3) map-ExtensionDataTypes (21) version13 (13)}
;

CUG-CheckInfo ::= SEQUENCE {
	cug-Interlock	CUG-Interlock,
	cug-OutgoingAccess	NULL			OPTIONAL,
	extensionContainer	ExtensionContainer	OPTIONAL,
	...}

NumberOfForwarding ::= INTEGER (1..5)

SendRoutingInfoArg ::= SEQUENCE {
	msisdn		[0] ISDN-AddressString,
	cug-CheckInfo	[1] CUG-CheckInfo	OPTIONAL,
	numberOfForwarding	[2] NumberOfForwarding	OPTIONAL,
	interrogationType	[3] InterrogationType,
	or-Interrogation	[4] NULL		OPTIONAL,
	or-Capability	[5] OR-Phase	OPTIONAL,
	gmsc-OrGsmSCF-Address	[6] ISDN-AddressString,
	--unused:callReferenceNumber	[7] CallReferenceNumber	OPTIONAL,
	--unused:forwardingReason	[8] ForwardingReason	OPTIONAL,
	--unused:basicServiceGroup	[9] Ext-BasicServiceCode	OPTIONAL,
	--unused:networkSignalInfo	[10] ExternalSignalInfo	OPTIONAL,
	--unused:camelInfo		[11] CamelInfo	OPTIONAL,
	--unused:suppressionOfAnnouncement	[12] SuppressionOfAnnouncement 	OPTIONAL,
	--unused:extensionContainer	[13] ExtensionContainer	OPTIONAL,
	...--unused:,
	--unused:alertingPattern	[14] AlertingPattern	OPTIONAL,
	--unused:ccbs-Call		[15] NULL			OPTIONAL,
	--unused:supportedCCBS-Phase	[16]	 SupportedCCBS-Phase	OPTIONAL,
	--unused:additionalSignalInfo	[17] Ext-ExternalSignalInfo	OPTIONAL,
	--unused:istSupportIndicator	[18] IST-SupportIndicator	OPTIONAL,
	--unused:pre-pagingSupported	[19]	NULL		OPTIONAL,
	--unused:callDiversionTreatmentIndicator	[20]	CallDiversionTreatmentIndicator	OPTIONAL,
	--unused:longFTN-Supported	[21]	NULL		OPTIONAL,
	--unused:suppress-VT-CSI	[22]	NULL		OPTIONAL,
	--unused:suppressIncomingCallBarring	[23]	NULL		OPTIONAL,
	--unused:gsmSCF-InitiatedCall	[24]	NULL		OPTIONAL,
	--unused:basicServiceGroup2	[25] Ext-BasicServiceCode	OPTIONAL,
	--unused:networkSignalInfo2	[26] ExternalSignalInfo	OPTIONAL,
	--unused:suppressMTSS	[27] SuppressMTSS	OPTIONAL,
	--unused:mtRoamingRetrySupported	[28] NULL		OPTIONAL,
	--unused:callPriority	[29]	EMLPP-Priority	OPTIONAL
	 }

--unused:SuppressionOfAnnouncement ::= NULL

--unused:SuppressMTSS ::= BIT STRING {
--unused:	suppressCUG	(0),
--unused:	suppressCCBS	(1) } (SIZE (2..16))
	--	Other bits than listed above shall be discarded

InterrogationType ::= ENUMERATED {
	basicCall  (0),
	forwarding  (1)}

OR-Phase ::= INTEGER (1..127)

CallReferenceNumber ::= OCTET STRING (SIZE (1..8))

--unused:ForwardingReason ::= ENUMERATED {
--unused:	notReachable  (0),
--unused:	busy  (1),
--unused:	noReply  (2)}

--unused:SupportedCCBS-Phase ::= INTEGER (1..127) 
-- exception handling:
-- Only value 1 is used.
-- Values in the ranges 2-127 are reserved for future use.
-- If received values 2-127 shall be mapped on to value 1.

--unused:CallDiversionTreatmentIndicator ::= OCTET STRING (SIZE(1))
--	callDiversionAllowed (xxxx xx01)
--	callDiversionNotAllowed (xxxx xx10)
--	network default is call diversion allowed

SendRoutingInfoRes ::= [3] SEQUENCE {
	imsi			[9] IMSI		OPTIONAL,
	-- IMSI must be present if SendRoutingInfoRes is not segmented.
	-- If the TC-Result-NL segmentation option is taken the IMSI must be
	-- present in one segmented transmission of SendRoutingInfoRes.
	extendedRoutingInfo	ExtendedRoutingInfo	OPTIONAL,
	cug-CheckInfo	[3] CUG-CheckInfo	OPTIONAL,                           --unused
	cugSubscriptionFlag	[6] NULL		OPTIONAL,                           --unused
	subscriberInfo	[7] SubscriberInfo	OPTIONAL,
	ss-List		[1] SS-List	OPTIONAL,                                       --unused
	basicService	[5] Ext-BasicServiceCode	OPTIONAL,                   --unused
	forwardingInterrogationRequired	[4] NULL		OPTIONAL,               --unused
	vmsc-Address	[2] ISDN-AddressString	OPTIONAL,                       --unused
	extensionContainer	[0] ExtensionContainer	OPTIONAL,                   --unused
	... --unused:,
	--unused:naea-PreferredCI	[10] NAEA-PreferredCI	OPTIONAL,
	-- naea-PreferredCI is included at the discretion of the HLR operator.
	--unused:ccbs-Indicators	[11] CCBS-Indicators	OPTIONAL,
	--unused:msisdn		[12] ISDN-AddressString	OPTIONAL,
	--unused:numberPortabilityStatus	[13] NumberPortabilityStatus	OPTIONAL,
	--unused:istAlertTimer	[14] IST-AlertTimerValue	OPTIONAL,
	--unused:supportedCamelPhasesInVMSC	[15]	SupportedCamelPhases	OPTIONAL,
	--unused:offeredCamel4CSIsInVMSC	[16] OfferedCamel4CSIs	OPTIONAL,
	--unused:routingInfo2	[17] RoutingInfo	OPTIONAL,
	--unused:ss-List2		[18] SS-List	OPTIONAL,
	--unused:basicService2	[19] Ext-BasicServiceCode	OPTIONAL,
	--unused:allowedServices	[20] AllowedServices	OPTIONAL,
	--unused:unavailabilityCause	[21] UnavailabilityCause	OPTIONAL,
	--unused:releaseResourcesSupported	[22] NULL		OPTIONAL,
	--unused:gsm-BearerCapability	[23] ExternalSignalInfo	OPTIONAL
	}

--unused:AllowedServices ::= BIT STRING {
--unused:	firstServiceAllowed	(0),
--unused:	secondServiceAllowed	(1) } (SIZE (2..8))
	--	firstService is the service indicated in the networkSignalInfo
	--	secondService is the service indicated in the networkSignalInfo2
	--	Other bits than listed above shall be discarded

--unused:UnavailabilityCause ::= ENUMERATED {
--unused:	bearerServiceNotProvisioned	(1),
--unused:	teleserviceNotProvisioned	(2),
--unused:	absentSubscriber	(3),
--unused:	busySubscriber	(4),
--unused:	callBarred	(5),
--unused:	cug-Reject	(6),
--unused:	...}
	--	exception handling: 
	--	Reception of other values than the ones listed shall result in the service
	--	being unavailable for that call.

CCBS-Indicators ::= SEQUENCE {
	ccbs-Possible	[0]	NULL		OPTIONAL,
	keepCCBS-CallIndicator	[1]	NULL		OPTIONAL,
	extensionContainer	[2]	ExtensionContainer	OPTIONAL,
	...}

RoutingInfo ::= CHOICE {
	roamingNumber	ISDN-AddressString,
	forwardingData	ForwardingData}

ForwardingData ::= SEQUENCE {
	forwardedToNumber	[5] ISDN-AddressString	OPTIONAL,
	-- When this datatype is sent from an HLR which supports CAMEL Phase 2
	-- to a GMSC which supports CAMEL Phase 2 the GMSC shall not check the
	-- format of the number
	--unused:forwardedToSubaddress	[4] ISDN-SubaddressString	OPTIONAL,
	--unused:forwardingOptions	[6] ForwardingOptions	OPTIONAL,
	--unused:extensionContainer	[7] ExtensionContainer	OPTIONAL,
	...--unused:,
	--unused:longForwardedToNumber	[8] FTN-AddressString	OPTIONAL--}

ProvideRoamingNumberArg ::= SEQUENCE {
	imsi			[0] IMSI,
	msc-Number	[1] ISDN-AddressString,
	msisdn		[2] ISDN-AddressString	OPTIONAL,
	--unused:lmsi			[4] LMSI		OPTIONAL,
	--unused:gsm-BearerCapability	[5] ExternalSignalInfo	OPTIONAL,
	--unused:networkSignalInfo	[6] ExternalSignalInfo	OPTIONAL,
	--unused:suppressionOfAnnouncement	[7] SuppressionOfAnnouncement	OPTIONAL,
	--unused:gmsc-Address	[8] ISDN-AddressString	OPTIONAL,
	--unused:callReferenceNumber	[9] CallReferenceNumber	OPTIONAL,
	--unused:or-Interrogation	[10] NULL		OPTIONAL,
	--unused:extensionContainer	[11] ExtensionContainer	OPTIONAL,
	... --unused:,
	--unused:alertingPattern	[12] AlertingPattern	OPTIONAL,
	--unused:ccbs-Call		[13] NULL		OPTIONAL,
	--unused:supportedCamelPhasesInInterrogatingNode	[15] SupportedCamelPhases	OPTIONAL,
	--unused:additionalSignalInfo	[14] Ext-ExternalSignalInfo	OPTIONAL,
	--unused:orNotSupportedInGMSC	[16] NULL		OPTIONAL,
	--unused:pre-pagingSupported	[17] NULL		OPTIONAL,
	--unused:longFTN-Supported	[18]	NULL		OPTIONAL,
	--unused:suppress-VT-CSI	[19]	NULL		OPTIONAL,
	--unused:offeredCamel4CSIsInInterrogatingNode	[20] OfferedCamel4CSIs	OPTIONAL,
	--unused:mtRoamingRetrySupported	[21] NULL		OPTIONAL,
	--unused:pagingArea	[22] PagingArea	OPTIONAL,
	--unused:callPriority	[23]	EMLPP-Priority	OPTIONAL
	 }

-- ProvideRoamingNumberRes ::= SEQUENCE {
-- 	roamingNumber	ISDN-AddressString,
-- 	extensionContainer	ExtensionContainer	OPTIONAL,
-- 	...,
-- 	releaseResourcesSupported	NULL			OPTIONAL }

ProvideRoamingNumberRes ::=  CHOICE { 
	data	SEQUENCE {
		roamingNumber	ISDN-AddressString,
		--unused:extensionContainer	ExtensionContainer	OPTIONAL,
		...--unused:,
		--unused:releaseResourcesSupported	NULL			OPTIONAL 
		},
	roamingNumber	ISDN-AddressString
	}

ResumeCallHandlingArg ::= SEQUENCE {
	callReferenceNumber	[0] CallReferenceNumber	OPTIONAL,          --unused
	basicServiceGroup	[1] Ext-BasicServiceCode	OPTIONAL,      --unused
	forwardingData	[2] ForwardingData	OPTIONAL,
	imsi			[3] IMSI		OPTIONAL,
	cug-CheckInfo	[4] CUG-CheckInfo	OPTIONAL,                  --unused
	o-CSI		[5] O-CSI		OPTIONAL,                          --unused
	extensionContainer	[7] ExtensionContainer	OPTIONAL,          --unused
	ccbs-Possible	[8]	NULL		OPTIONAL,                      --unused
	msisdn		[9]	ISDN-AddressString	OPTIONAL,
	--unused:uu-Data		[10] UU-Data	OPTIONAL,
	--unused:allInformationSent	[11] NULL		OPTIONAL,
	...--unused:,
	--unused:d-csi		[12]	D-CSI	OPTIONAL,
	--unused:o-BcsmCamelTDPCriteriaList 	[13]	O-BcsmCamelTDPCriteriaList 	OPTIONAL,
	--unused:basicServiceGroup2	[14] Ext-BasicServiceCode	OPTIONAL,
	--unused:mtRoamingRetry	[15] NULL		OPTIONAL
	 }

--unused:UU-Data ::= SEQUENCE {
--unused:	uuIndicator	[0] UUIndicator	OPTIONAL,
--unused:	uui			[1] UUI		OPTIONAL,
--unused:	uusCFInteraction	[2] NULL		OPTIONAL,
--unused:	extensionContainer	[3] ExtensionContainer	OPTIONAL,
--unused:	...}

--unused:UUIndicator ::= OCTET STRING (SIZE (1))
	-- Octets are coded according to ETS 300 356

--unused:UUI  ::= OCTET STRING (SIZE (1..131))
	-- Octets are coded according to ETS 300 356

--unused:ResumeCallHandlingRes ::= SEQUENCE {
--unused:	extensionContainer	ExtensionContainer	OPTIONAL,
--unused:	...}

--unused:CamelInfo ::= SEQUENCE {
--unused:	supportedCamelPhases	SupportedCamelPhases,
--unused:	suppress-T-CSI	NULL			OPTIONAL,
--unused:	extensionContainer	ExtensionContainer	OPTIONAL,
--unused:	... ,
--unused:	offeredCamel4CSIs	[0] OfferedCamel4CSIs	OPTIONAL }

ExtendedRoutingInfo ::= CHOICE {
	routingInfo	RoutingInfo,
	camelRoutingInfo	[8] CamelRoutingInfo}

CamelRoutingInfo ::= SEQUENCE {
	forwardingData	ForwardingData	OPTIONAL,
	gmscCamelSubscriptionInfo	[0] GmscCamelSubscriptionInfo,
	--unused:extensionContainer	[1] ExtensionContainer	OPTIONAL,
	...}

GmscCamelSubscriptionInfo ::= SEQUENCE {
	t-CSI		[0] T-CSI	OPTIONAL,
	o-CSI		[1] O-CSI	OPTIONAL,
	extensionContainer	[2] ExtensionContainer	OPTIONAL,
	...,
	o-BcsmCamelTDP-CriteriaList	[3] O-BcsmCamelTDPCriteriaList	OPTIONAL,
	t-BCSM-CAMEL-TDP-CriteriaList	[4]	T-BCSM-CAMEL-TDP-CriteriaList	OPTIONAL,
	d-csi		[5]	D-CSI	OPTIONAL}

SetReportingStateArg ::= SEQUENCE {
	imsi			[0]	IMSI		OPTIONAL,
	--unused:lmsi			[1]	LMSI		OPTIONAL,
	--unused:ccbs-Monitoring	[2]	ReportingState	OPTIONAL,
	--unused:extensionContainer	[3]	ExtensionContainer	OPTIONAL,
	...}

--unused:ReportingState ::= ENUMERATED {
--unused:	stopMonitoring	(0),
--unused:	startMonitoring	(1),
--unused:	...}
	-- exception handling:
	-- reception of values 2-10 shall be mapped to 'stopMonitoring' 
	-- reception of values > 10 shall be mapped to 'startMonitoring'

--unused:SetReportingStateRes ::= SEQUENCE{
--unused:	ccbs-SubscriberStatus 	[0]	CCBS-SubscriberStatus	OPTIONAL,
--unused:	extensionContainer	[1]	ExtensionContainer	OPTIONAL,
--unused:	...}

CCBS-SubscriberStatus ::= ENUMERATED {
	ccbsNotIdle 	(0),
	ccbsIdle 		(1),
	ccbsNotReachable	(2),
	...}
	--  exception handling: 
	--  reception of values 3-10 shall be mapped to 'ccbsNotIdle'
	--  reception of values 11-20 shall be mapped to 'ccbsIdle'
	--  reception of values > 20 shall be mapped to 'ccbsNotReachable' 

StatusReportArg ::= SEQUENCE{
	imsi 		[0]	IMSI,
	--unused:eventReportData	[1]	EventReportData	OPTIONAL,
	--unused:callReportdata	[2]	CallReportData	OPTIONAL,
	--unused:extensionContainer	[3]	ExtensionContainer	OPTIONAL,
	...}

--unused:EventReportData ::= SEQUENCE{
--unused:	ccbs-SubscriberStatus	[0]	CCBS-SubscriberStatus	OPTIONAL,
--unused:	extensionContainer	[1]	ExtensionContainer	OPTIONAL,
--unused:	...}

--unused:CallReportData ::= SEQUENCE{
--unused:	monitoringMode	[0]	MonitoringMode	OPTIONAL,
--unused:	callOutcome	[1]	CallOutcome	OPTIONAL,
--unused:	extensionContainer	[2]	ExtensionContainer	OPTIONAL,
--unused:	...}

--unused:MonitoringMode ::= ENUMERATED {
--unused:	a-side		(0),
--unused:	b-side		(1),
--unused:	...}
	--	exception handling: 
	--  reception of values 2-10 shall be mapped 'a-side'
	--  reception of values > 10 shall be mapped to 'b-side'

--unused:CallOutcome ::= ENUMERATED {
--unused:	success		(0),
--unused:	failure		(1),
--unused:	busy			(2),
--unused:	...}
	--	exception handling: 
	--  reception of values 3-10 shall be mapped to 'success'
	--  reception of values 11-20 shall be mapped to 'failure'
	--  reception of values > 20 shall be mapped to 'busy'

--unused:StatusReportRes ::= SEQUENCE {
--unused:	extensionContainer	[0]	ExtensionContainer	OPTIONAL,
--unused:	...}

RemoteUserFreeArg ::= SEQUENCE{
	imsi			[0]	IMSI,
	callInfo		[1]	ExternalSignalInfo,       --unused
	ccbs-Feature	[2]	CCBS-Feature,             --unused
	translatedB-Number	[3]	ISDN-AddressString,   --unused
	--unused:replaceB-Number	[4] 	NULL		OPTIONAL,
	--unused:alertingPattern	[5]	AlertingPattern	OPTIONAL,
	--unused:extensionContainer	[6]	ExtensionContainer	OPTIONAL,
	...}

--unused:RemoteUserFreeRes ::= SEQUENCE{
--unused:	ruf-Outcome	[0]	RUF-Outcome,
--unused:	extensionContainer	[1]	ExtensionContainer	OPTIONAL,
--unused:	...}

--unused:RUF-Outcome ::= ENUMERATED{
--unused:	accepted (0),
--unused:	rejected (1),
--unused:	noResponseFromFreeMS (2), - - T4 Expiry
--unused:	noResponseFromBusyMS (3), - - T10 Expiry
--unused:	udubFromFreeMS (4),
--unused:	udubFromBusyMS (5),
--unused:	...}
	-- exception handling:
	-- reception of values 6-20 shall be mapped to 'accepted'
	-- reception of values 21-30 shall be mapped to 'rejected'
	-- reception of values 31-40 shall be mapped to 'noResponseFromFreeMS'
	-- reception of values 41-50 shall be mapped to 'noResponseFromBusyMS'
	-- reception of values 51-60 shall be mapped to 'udubFromFreeMS'
	-- reception of values > 60 shall be mapped to 'udubFromBusyMS'

IST-AlertArg ::= SEQUENCE{
	imsi			[0]	IMSI,
	--unused:extensionContainer	[1]	ExtensionContainer	OPTIONAL,
	...}

--unused:IST-AlertRes ::= SEQUENCE{
--unused:	istAlertTimer	[0]	IST-AlertTimerValue 	OPTIONAL,
--unused:	istInformationWithdraw	[1]	NULL		OPTIONAL,
--unused:	callTerminationIndicator	[2]	CallTerminationIndicator	OPTIONAL,
--unused:	extensionContainer	[3]	ExtensionContainer	OPTIONAL,
--unused:	...}

IST-CommandArg ::= SEQUENCE{
	imsi			[0]	IMSI,
	--unused:extensionContainer	[1]	ExtensionContainer	OPTIONAL,
	...}

--unused:IST-CommandRes ::= SEQUENCE{
--unused:	extensionContainer	ExtensionContainer	OPTIONAL,
--unused:	...}

--unused:CallTerminationIndicator ::= ENUMERATED {
--unused:	terminateCallActivityReferred	(0),
--unused:	terminateAllCallActivities	(1),
--unused:	...}
	-- exception handling:
	-- reception of values 2-10 shall be mapped to ' terminateCallActivityReferred ' 
	-- reception of values > 10 shall be mapped to ' terminateAllCallActivities '

	-- In MSCs not supporting linkage of all call activities, any value received shall
	-- be interpreted as ' terminateCallActivityReferred '

ReleaseResourcesArg ::= SEQUENCE{
	msrn			ISDN-AddressString, 
	--unused:extensionContainer	ExtensionContainer	OPTIONAL,
	...}

--unused:ReleaseResourcesRes ::= SEQUENCE{
--unused:	extensionContainer	ExtensionContainer	OPTIONAL,
--unused:	...}

END
