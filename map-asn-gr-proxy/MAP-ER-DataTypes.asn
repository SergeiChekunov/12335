-- ETSI TS 129 002 V10.4.0 (2011-10)
-- 17.7.7  Error data types

MAP-ER-DataTypes {
	itu-t identified-organization (4) etsi (0) mobileDomain (0)
	gsm-Network (1) modules (3) map-ER-DataTypes (17) version13 (13)}

DEFINITIONS

IMPLICIT TAGS

::=

BEGIN

EXPORTS
	--unused:RoamingNotAllowedParam,
	--unused:CallBarredParam,
	--unused:CUG-RejectParam,
	--unused:SS-IncompatibilityCause,
	--unused:PW-RegistrationFailureCause,
	--unused:SM-DeliveryFailureCause,
	--unused:SystemFailureParam,
	--unused:DataMissingParam,
	--unused:UnexpectedDataParam,
	--unused:FacilityNotSupParam,
	--unused:OR-NotAllowedParam,
	--unused:UnknownSubscriberParam,
	--unused:NumberChangedParam,
	--unused:UnidentifiedSubParam,
	--unused:IllegalSubscriberParam,
	--unused:IllegalEquipmentParam,
	--unused:BearerServNotProvParam,
	--unused:TeleservNotProvParam,
	--unused:TracingBufferFullParam,
	--unused:NoRoamingNbParam,
	--unused:AbsentSubscriberParam,
	--unused:BusySubscriberParam,
	--unused:NoSubscriberReplyParam,
	--unused:ForwardingViolationParam,
	--unused:ForwardingFailedParam,
	--unused:ATI-NotAllowedParam,
	--unused:SubBusyForMT-SMS-Param,
	--unused:MessageWaitListFullParam,
	--unused:AbsentSubscriberSM-Param,
	AbsentSubscriberDiagnosticSM --unused:,
	--unused:ResourceLimitationParam,
	--unused:NoGroupCallNbParam,
	--unused:IncompatibleTerminalParam,
	--unused:ShortTermDenialParam,
	--unused:LongTermDenialParam,
	--unused:UnauthorizedRequestingNetwork-Param,
	--unused:UnauthorizedLCSClient-Param,
	--unused:PositionMethodFailure-Param,
	--unused:UnknownOrUnreachableLCSClient-Param,
	--unused:MM-EventNotSupported-Param,
	--unused:ATSI-NotAllowedParam,
	--unused:ATM-NotAllowedParam,
	--unused:IllegalSS-OperationParam,
	--unused:SS-NotAvailableParam,
	--unused:SS-SubscriptionViolationParam,
	--unused:InformationNotAvailableParam,
	--unused:TargetCellOutsideGCA-Param,
	--unused:OngoingGroupCallParam

	;

--unused:IMPORTS
--unused:	SS-Status
--unused:FROM MAP-SS-DataTypes {
--unused:	itu-t identified-organization (4) etsi (0) mobileDomain (0)
--unused:	gsm-Network (1) modules (3) map-SS-DataTypes (14) version13 (13)}
--unused:
--unused:	SignalInfo,
--unused:	BasicServiceCode,
--unused:	NetworkResource,
--unused:	AdditionalNetworkResource
--unused:FROM MAP-CommonDataTypes {
--unused:	itu-t identified-organization (4) etsi (0) mobileDomain (0)
--unused:	gsm-Network (1) modules (3) map-CommonDataTypes (18) version13 (13)}
--unused:
--unused:	SS-Code
--unused:FROM MAP-SS-Code {
--unused:	itu-t identified-organization (4) etsi (0) mobileDomain (0)
--unused:	gsm-Network (1) modules (3) map-SS-Code (15) version13 (13)}
--unused:
--unused:	ExtensionContainer
--unused:FROM MAP-ExtensionDataTypes {
--unused:	itu-t identified-organization (4) etsi (0) mobileDomain (0)
--unused:	gsm-Network (1) modules (3) map-ExtensionDataTypes (21) version13 (13)}
--unused:	;

--unused:RoamingNotAllowedParam  ::= SEQUENCE {
--unused:	roamingNotAllowedCause  RoamingNotAllowedCause,
--unused:	extensionContainer  ExtensionContainer  OPTIONAL,
--unused:	...,
--unused:	additionalRoamingNotAllowedCause  [0] AdditionalRoamingNotAllowedCause OPTIONAL }
--unused:
--unused:- -  if the additionalRoamingNotallowedCause is received by the MSC/VLR or SGSN then the
--unused:- -  roamingNotAllowedCause shall be discarded.
--unused:
--unused:AdditionalRoamingNotAllowedCause  ::= ENUMERATED {
--unused:	supportedRAT-TypesNotAllowed (0),
--unused:	...}
--unused:
--unused:RoamingNotAllowedCause  ::= ENUMERATED {
--unused:	plmnRoamingNotAllowed  (0),
--unused:	operatorDeterminedBarring  (3)}
--unused:
--unused:CallBarredParam ::= CHOICE {
--unused:	callBarringCause  CallBarringCause,
--unused:	- - call BarringCause must not be used in version 3 and higher
--unused:	extensibleCallBarredParam  ExtensibleCallBarredParam
--unused:	- - extensibleCallBarredParam must not be used in version <3
--unused:	}
--unused:
--unused:CallBarringCause ::= ENUMERATED {
--unused:	barringServiceActive  (0),
--unused:	operatorBarring  (1)}
--unused:
--unused:ExtensibleCallBarredParam ::= SEQUENCE {
--unused:	callBarringCause  CallBarringCause  OPTIONAL,
--unused:	extensionContainer  ExtensionContainer  OPTIONAL,
--unused:	... ,
--unused:	unauthorisedMessageOriginator  [1] NULL    OPTIONAL }
--unused:
--unused:CUG-RejectParam ::= SEQUENCE {
--unused:	cug-RejectCause  CUG-RejectCause  OPTIONAL,
--unused:	extensionContainer  ExtensionContainer  OPTIONAL,
--unused:	...}
--unused:
--unused:CUG-RejectCause ::= ENUMERATED {
--unused:	incomingCallsBarredWithinCUG  (0),
--unused:	subscriberNotMemberOfCUG  (1),
--unused:	requestedBasicServiceViolatesCUG-Constraints  (5),
--unused:	calledPartySS-InteractionViolation  (7)}
--unused:
--unused:SS-IncompatibilityCause ::= SEQUENCE {
--unused:	ss-Code   [1] SS-Code  OPTIONAL,
--unused:	basicService  BasicServiceCode  OPTIONAL,
--unused:	ss-Status  [4] SS-Status OPTIONAL,
--unused:	...}
--unused:
--unused:PW-RegistrationFailureCause  ::= ENUMERATED {
--unused:	undetermined  (0),
--unused:	invalidFormat  (1),
--unused:	newPasswordsMismatch  (2)}
--unused:
--unused:SM-EnumeratedDeliveryFailureCause ::= ENUMERATED {
--unused:	memoryCapacityExceeded  (0),
--unused:	equipmentProtocolError  (1),
--unused:	equipmentNotSM-Equipped  (2),
--unused:	unknownServiceCentre  (3),
--unused:	sc-Congestion  (4),
--unused:	invalidSME-Address  (5),
--unused:	subscriberNotSC-Subscriber  (6)}
--unused:
--unused:SM-DeliveryFailureCause ::= SEQUENCE {
--unused:	sm-EnumeratedDeliveryFailureCause SM-EnumeratedDeliveryFailureCause,
--unused:	diagnosticInfo  SignalInfo  OPTIONAL,
--unused:	extensionContainer  ExtensionContainer  OPTIONAL,
--unused:	...}
--unused:
--unused:AbsentSubscriberSM-Param ::= SEQUENCE {
--unused:	absentSubscriberDiagnosticSM  AbsentSubscriberDiagnosticSM  OPTIONAL,
--unused:	- - AbsentSubscriberDiagnosticSM can be either for non-GPRS
--unused:	- - or for GPRS
--unused:	extensionContainer  ExtensionContainer  OPTIONAL,
--unused:	...,
--unused:	additionalAbsentSubscriberDiagnosticSM    [0]  AbsentSubscriberDiagnosticSM OPTIONAL }
--unused:	- - if received, additionalAbsentSubscriberDiagnosticSM
--unused:	- - is for GPRS and absentSubscriberDiagnosticSM is
--unused:	- - for non-GPRS

AbsentSubscriberDiagnosticSM ::= INTEGER (0..255)
	-- AbsentSubscriberDiagnosticSM values are defined in 3GPP TS 23.040

--unused:SystemFailureParam ::= CHOICE {
--unused:	networkResource  NetworkResource,
--unused:	 - - networkResource must not be used in version 3
--unused:	extensibleSystemFailureParam  ExtensibleSystemFailureParam
--unused:	 - - extensibleSystemFailureParam must not be used in version <3
--unused:	}
--unused:
--unused:ExtensibleSystemFailureParam ::= SEQUENCE {
--unused:	networkResource  NetworkResource  OPTIONAL,
--unused:	extensionContainer  ExtensionContainer  OPTIONAL,
--unused:	...,
--unused:	additionalNetworkResource  [0] AdditionalNetworkResource  OPTIONAL,
--unused:	failureCauseParam  [1] FailureCauseParam  OPTIONAL }
--unused:
--unused:FailureCauseParam  ::= ENUMERATED {
--unused:	limitReachedOnNumberOfConcurrentLocationRequests (0),
--unused:	... }
--unused:	 - - if unknown value is received in  FailureCauseParam it shall be ignored
--unused:
--unused:
--unused:DataMissingParam ::= SEQUENCE {
--unused:	extensionContainer  ExtensionContainer  OPTIONAL,
--unused:	...}
--unused:
--unused:UnexpectedDataParam  ::= SEQUENCE {
--unused:	extensionContainer  ExtensionContainer  OPTIONAL,
--unused:	...}
--unused:
--unused:FacilityNotSupParam  ::= SEQUENCE {
--unused:	extensionContainer  ExtensionContainer  OPTIONAL,
--unused:	...,
--unused:	shapeOfLocationEstimateNotSupported [0] NULL   OPTIONAL,
--unused:	neededLcsCapabilityNotSupportedInServingNode [1] NULL  OPTIONAL }
--unused:
--unused:OR-NotAllowedParam ::= SEQUENCE {
--unused:	extensionContainer  ExtensionContainer  OPTIONAL,
--unused:	...}
--unused:
--unused:UnknownSubscriberParam  ::= SEQUENCE {
--unused:	extensionContainer  ExtensionContainer  OPTIONAL,
--unused:	...,
--unused:	unknownSubscriberDiagnostic  UnknownSubscriberDiagnostic  OPTIONAL}
--unused:
--unused:UnknownSubscriberDiagnostic  ::= ENUMERATED {
--unused:	imsiUnknown  (0),
--unused:	gprs-eps-SubscriptionUnknown  (1),
--unused:	...,
--unused:	npdbMismatch  (2)}
--unused:	- - if unknown values are received in
--unused:	- - UnknownSubscriberDiagnostic they shall be discarded
--unused:
--unused:NumberChangedParam ::= SEQUENCE {
--unused:	extensionContainer  ExtensionContainer  OPTIONAL,
--unused:	...}
--unused:
--unused:UnidentifiedSubParam ::= SEQUENCE {
--unused:	extensionContainer  ExtensionContainer  OPTIONAL,
--unused:	...}
--unused:
--unused:IllegalSubscriberParam  ::= SEQUENCE {
--unused:	extensionContainer  ExtensionContainer  OPTIONAL,
--unused:	...}
--unused:
--unused:IllegalEquipmentParam ::= SEQUENCE {
--unused:	extensionContainer  ExtensionContainer  OPTIONAL,
--unused:	...}
--unused:
--unused:BearerServNotProvParam  ::= SEQUENCE {
--unused:	extensionContainer  ExtensionContainer  OPTIONAL,
--unused:	...}
--unused:
--unused:TeleservNotProvParam ::= SEQUENCE {
--unused:	extensionContainer  ExtensionContainer  OPTIONAL,
--unused:	...}
--unused:
--unused:TracingBufferFullParam  ::= SEQUENCE {
--unused:	extensionContainer  ExtensionContainer  OPTIONAL,
--unused:	...}
--unused:
--unused:NoRoamingNbParam ::= SEQUENCE {
--unused:	extensionContainer  ExtensionContainer  OPTIONAL,
--unused:	...}
--unused:
--unused:AbsentSubscriberParam ::= SEQUENCE {
--unused:	extensionContainer  ExtensionContainer  OPTIONAL,
--unused:	...,
--unused:	absentSubscriberReason  [0] AbsentSubscriberReason  OPTIONAL}
--unused:
--unused:AbsentSubscriberReason  ::= ENUMERATED {
--unused:	imsiDetach (0),
--unused:	restrictedArea (1),
--unused:	noPageResponse (2),
--unused:	... ,
--unused:	purgedMS (3),
--unused:	mtRoamingRetry (4),
--unused:	busySubscriber (5)}
--unused:- - exception handling: at reception of other values than the ones listed the
--unused:- - AbsentSubscriberReason shall be ignored.
--unused:- - The AbsentSubscriberReason: purgedMS is defined for the Super-Charger feature
--unused:- - (see TS 23.116). If this value is received in a Provide Roaming Number response
--unused:- - it shall be mapped to the AbsentSubscriberReason: imsiDetach in the Send Routeing
--unused:- - Information response
--unused:- - The AbsentSubscriberReason: mtRoamingRetry is used during MT Roaming Retry,
--unused:- - see 3GPP TS 23.018[97].
--unused:- - The AbsentSubscriberReason: busySubscriber is used during MT Roaming Forwarding,
--unused:- - see 3GPP TS 23.018[97].
--unused:
--unused:BusySubscriberParam  ::= SEQUENCE {
--unused:	extensionContainer  ExtensionContainer  OPTIONAL,
--unused:	...,
--unused:	ccbs-Possible  [0] NULL   OPTIONAL,
--unused:	ccbs-Busy  [1] NULL  OPTIONAL}
--unused:
--unused:NoSubscriberReplyParam  ::= SEQUENCE {
--unused:	extensionContainer  ExtensionContainer  OPTIONAL,
--unused:	...}
--unused:
--unused:ForwardingViolationParam  ::= SEQUENCE {
--unused:	extensionContainer  ExtensionContainer  OPTIONAL,
--unused:	...}
--unused:
--unused:ForwardingFailedParam ::= SEQUENCE {
--unused:	extensionContainer  ExtensionContainer  OPTIONAL,
--unused:	...}
--unused:
--unused:ATI-NotAllowedParam  ::= SEQUENCE {
--unused:	extensionContainer  ExtensionContainer  OPTIONAL,
--unused:	...}
--unused:
--unused:ATSI-NotAllowedParam ::=  SEQUENCE {
--unused:	extensionContainer  ExtensionContainer  OPTIONAL,
--unused:	...}
--unused:
--unused:ATM-NotAllowedParam ::= SEQUENCE {
--unused:	extensionContainer  ExtensionContainer  OPTIONAL,
--unused:	...}
--unused:
--unused:IllegalSS-OperationParam  ::= SEQUENCE {
--unused:	extensionContainer  ExtensionContainer  OPTIONAL,
--unused:	...}
--unused:
--unused:SS-NotAvailableParam ::= SEQUENCE {
--unused:	extensionContainer  ExtensionContainer  OPTIONAL,
--unused:	...}
--unused:
--unused:SS-SubscriptionViolationParam  ::= SEQUENCE {
--unused:	extensionContainer  ExtensionContainer  OPTIONAL,
--unused:	...}
--unused:
--unused:InformationNotAvailableParam ::= SEQUENCE {
--unused:	extensionContainer  ExtensionContainer  OPTIONAL,
--unused:	...}
--unused:
--unused:SubBusyForMT-SMS-Param  ::= SEQUENCE {
--unused:	extensionContainer  ExtensionContainer  OPTIONAL,
--unused:	... ,
--unused:	gprsConnectionSuspended  NULL    OPTIONAL }
--unused:	 - - If GprsConnectionSuspended is not understood it shall
--unused:	 - - be discarded
--unused:
--unused:MessageWaitListFullParam  ::= SEQUENCE {
--unused:	extensionContainer  ExtensionContainer  OPTIONAL,
--unused:	...}
--unused:
--unused:ResourceLimitationParam ::= SEQUENCE {
--unused:	extensionContainer  ExtensionContainer  OPTIONAL,
--unused:	...}
--unused:
--unused:NoGroupCallNbParam ::= SEQUENCE {
--unused:	extensionContainer  ExtensionContainer  OPTIONAL,
--unused:	...}
--unused:
--unused:IncompatibleTerminalParam ::= SEQUENCE {
--unused:	extensionContainer  ExtensionContainer  OPTIONAL,
--unused:	...}
--unused:
--unused:ShortTermDenialParam ::= SEQUENCE {
--unused:	...}
--unused:
--unused:LongTermDenialParam  ::= SEQUENCE {
--unused:	...}
--unused:
--unused:UnauthorizedRequestingNetwork-Param ::= SEQUENCE {
--unused:	extensionContainer  ExtensionContainer  OPTIONAL,
--unused:	...}
--unused:
--unused:UnauthorizedLCSClient-Param ::= SEQUENCE {
--unused:	unauthorizedLCSClient-Diagnostic [0] UnauthorizedLCSClient-Diagnostic OPTIONAL,
--unused:	extensionContainer  [1] ExtensionContainer    OPTIONAL,
--unused:	... }
--unused:
--unused:UnauthorizedLCSClient-Diagnostic ::= ENUMERATED {
--unused:	noAdditionalInformation (0),
--unused:	clientNotInMSPrivacyExceptionList (1),
--unused:	callToClientNotSetup (2),
--unused:	privacyOverrideNotApplicable (3),
--unused:	disallowedByLocalRegulatoryRequirements (4),
--unused:	...,
--unused:	unauthorizedPrivacyClass (5),
--unused:	unauthorizedCallSessionUnrelatedExternalClient (6),
--unused:	unauthorizedCallSessionRelatedExternalClient (7) }
--unused:- - exception handling:
--unused:- - any unrecognized value shall be ignored
--unused:
--unused:PositionMethodFailure-Param ::= SEQUENCE {
--unused:	positionMethodFailure-Diagnostic [0] PositionMethodFailure-Diagnostic OPTIONAL,
--unused:	extensionContainer  [1] ExtensionContainer    OPTIONAL,
--unused:	... }
--unused:
--unused:PositionMethodFailure-Diagnostic ::= ENUMERATED {
--unused:	congestion  (0),
--unused:	insufficientResources  (1),
--unused:	insufficientMeasurementData  (2),
--unused:	inconsistentMeasurementData  (3),
--unused:	locationProcedureNotCompleted  (4),
--unused:	locationProcedureNotSupportedByTargetMS  (5),
--unused:	qoSNotAttainable  (6),
--unused:	positionMethodNotAvailableInNetwork (7),
--unused:	positionMethodNotAvailableInLocationArea (8),
--unused:	... }
--unused:- - exception handling:
--unused:- -  any unrecognized value shall be ignored
--unused:
--unused:UnknownOrUnreachableLCSClient-Param ::= SEQUENCE {
--unused:	extensionContainer  ExtensionContainer  OPTIONAL,
--unused:	...}
--unused:
--unused:MM-EventNotSupported-Param ::= SEQUENCE {
--unused:	extensionContainer  ExtensionContainer  OPTIONAL,
--unused:	...}
--unused:
--unused:TargetCellOutsideGCA-Param ::= SEQUENCE {
--unused:	extensionContainer  ExtensionContainer  OPTIONAL,
--unused:	...}
--unused:
--unused:OngoingGroupCallParam ::= SEQUENCE {
--unused:	extensionContainer  ExtensionContainer  OPTIONAL,
--unused:	...}

END
